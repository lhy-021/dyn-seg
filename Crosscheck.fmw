FME workspace Crosscheck.fmw

Readers:
- GEODATABASE_SDE_1: GEODATABASE_SDE
- SPATIALITE_1: SPATIALITE from $(FME_MF_DIR)dynseg-result.sqlite
- XLSXR_1: XLSXR from $(FME_MF_DIR)T_ROAD_INVENTORY.xlsx

Note: SDE
RH.T_ROAD_INVENTORY (reader GEODATABASE_SDE_1)
    attributes: ID char(38), ROUTEID char(14), FROMMEASURE double, TOMEASURE double, ACCESS_CONTROL_CD char(1), ACCESS_CONTROL_OPNL_CD integer, BASE_TYPE_LEFT_CD char(1), BASE_TYPE_RIGHT_CD char(1), COUNTY char(3), DIRECTION_OF_TRAVEL_CD char(1), D_DISTRICT_ID char(2), DIVIDED_HWY_IND char(1), FACILITY_TYPE_CD integer, FAP_IND char(1), FUNCTION_CLASS_CD integer, SAMPLE_ID char(12), LANE_WIDTH_NBR integer, LEAVE_IND char(1), REENTER_IND char(1), MAINTENANCE_AUTHORITY_CD integer, MEDIAN_TYPE_CD integer, MEDIAN_WIDTH_NBR integer, COUNTY_CODE char(3), COUNTY_CODE_LEFT char(3), COUNTY_CODE_RIGHT char(3), COUNTY_SPLIT_INDICATOR char(1), JURISDICTION char(1), MILEAGE_CLASS smallint, MUNI_CODE_LEFT char(50), MUNI_CODE_RIGHT char(50),
      OVERLAP_INDICATOR char(1), ROADWAY_CLASS smallint, STATE_CODE_LEFT char(2), STATE_CODE_RIGHT char(2), TAG_REVENUE_ELIGIBLE smallint, TWP_CODE_LEFT char(50), TWP_CODE_RIGHT char(50), NHS_CD char(1), NHS_INTERMODAL_ROUTE_CD char(2), OWNERSHIP_CD integer, PRIORITY_SYSTEM_CD char(1), ROADWAY_WIDTH smallint, SEGMENT_DESCRIPTION_TXT char(255), SCENIC_BYWAY_CD char(1), SCENIC_ROUTE_NUMBER char(2), SHOULDER_TOTAL_WIDTH_LT integer, SHOULDER_TOTAL_WIDTH_RT integer, SHOULDER_PVD_WIDTH_IN_LT integer, SHOULDER_PVD_WIDTH_IN_RT integer, SHOULDER_PVD_WIDTH_OUT_LT integer, SHOULDER_PVD_WIDTH_OUT_RT integer, SHOULDER_TYPE_CD integer, SPEED_LIMIT_NBR integer, STREET_PREFIX_DIR_CD char(1), STREET_NAME char(100), STREET_SUFFIX_CD char(4), STREET_DIR_SUFFIX_CD char(2), SURFACE_TYPE_LEFT_CD char(1), SURFACE_TYPE_RIGHT_CD char(1), SURFACE_WIDTH_LEFT integer,
      SURFACE_WIDTH_RIGHT integer, LANES_NBR integer, TRANSACTION_REASON_CODE char(1), TRANSACTION_COMMENT char(100), TRUCK_ROUTE_IND char(1), AREA_CODE_NBR char(9)
    -> AttributeRounder
AttributeRounder
    ROUND_TYPE = Nearest
    SRC_ATTRS = FROMMEASURE TOMEASURE
    PLACES = 3
    -> AttributeRemover
Note: SPATIALITE
RH_T_ROAD_INVENTORY (reader SPATIALITE_1) [off]
    attributes: ID string(38), ROUTEID string(14), FROMMEASURE real(20,10), TOMEASURE real(20,10), ACCESS_CONTROL_CD string(1), ACCESS_CONTROL_OPNL_CD integer, BASE_TYPE_LEFT_CD string(1), BASE_TYPE_RIGHT_CD string(1), COUNTY string(3), DIRECTION_OF_TRAVEL_CD string(1), D_DISTRICT_ID string(2), DIVIDED_HWY_IND string(1), FACILITY_TYPE_CD integer, FAP_IND string(1), FUNCTION_CLASS_CD integer, SAMPLE_ID string(12), LANE_WIDTH_NBR integer, LEAVE_IND string(1), REENTER_IND string(1), MAINTENANCE_AUTHORITY_CD integer, MEDIAN_TYPE_CD integer, MEDIAN_WIDTH_NBR integer, COUNTY_CODE string(3), COUNTY_CODE_LEFT string(3), COUNTY_CODE_RIGHT string(3), COUNTY_SPLIT_INDICATOR string(1), JURISDICTION string(1), MILEAGE_CLASS integer, MUNI_CODE_LEFT string(50), MUNI_CODE_RIGHT string(50),
      OVERLAP_INDICATOR string(1), ROADWAY_CLASS integer, STATE_CODE_LEFT string(2), STATE_CODE_RIGHT string(2), TAG_REVENUE_ELIGIBLE integer, TWP_CODE_LEFT string(50), TWP_CODE_RIGHT string(50), NHS_CD string(1), NHS_INTERMODAL_ROUTE_CD string(2), OWNERSHIP_CD integer, PRIORITY_SYSTEM_CD string(1), ROADWAY_WIDTH integer, SEGMENT_DESCRIPTION_TXT string(255), SCENIC_BYWAY_CD string(1), SCENIC_ROUTE_NUMBER string(2), SHOULDER_TOTAL_WIDTH_LT integer, SHOULDER_TOTAL_WIDTH_RT integer, SHOULDER_PVD_WIDTH_IN_LT integer, SHOULDER_PVD_WIDTH_IN_RT integer, SHOULDER_PVD_WIDTH_OUT_LT integer, SHOULDER_PVD_WIDTH_OUT_RT integer, SHOULDER_TYPE_CD integer, SPEED_LIMIT_NBR integer, STREET_PREFIX_DIR_CD string(1), STREET_NAME string(100), STREET_SUFFIX_CD string(4), STREET_DIR_SUFFIX_CD string(2), SURFACE_TYPE_LEFT_CD string(1), SURFACE_TYPE_RIGHT_CD string(1), SURFACE_WIDTH_LEFT integer,
      SURFACE_WIDTH_RIGHT integer, LANES_NBR integer, TRANSACTION_REASON_CODE string(1), TRANSACTION_COMMENT string(100), TRUCK_ROUTE_IND string(1), AREA_CODE_NBR string(9)
    -> Tester
    -> AttributeManager
Tester [off]
    TEST_MODE = Automatic
    TEST_DESCRIPTION = ""
    TEST_CLAUSE = TEST @Value(ROUTEID) = SWOOUS00020**C
    BOOL_OP = OR
    PASSED -> AttributeManager
RH.T_ROAD_INVENTORY (reader XLSXR_1)
    attributes: ID string, ROUTEID char(15), FROMMEASURE number(6,3), TOMEASURE number(6,3), ACCESS_CONTROL_CD char(2), ACCESS_CONTROL_OPNL_CD number(2,0), BASE_TYPE_LEFT_CD char(2), BASE_TYPE_RIGHT_CD char(2), COUNTY char(4), DIRECTION_OF_TRAVEL_CD string, D_DISTRICT_ID number(3,0), DIVIDED_HWY_IND char(2), FACILITY_TYPE_CD number(2,0), FAP_IND char(2), FUNCTION_CLASS_CD number(2,0), SAMPLE_ID number(13,0), LANE_WIDTH_NBR number(3,0), LEAVE_IND char(2), REENTER_IND char(2), MAINTENANCE_AUTHORITY_CD number(2,0), MEDIAN_TYPE_CD number(2,0), MEDIAN_WIDTH_NBR number(3,0), COUNTY_CODE char(4), COUNTY_CODE_LEFT char(4), COUNTY_CODE_RIGHT char(4), COUNTY_SPLIT_INDICATOR string, JURISDICTION char(2), MILEAGE_CLASS number(2,0), MUNI_CODE_LEFT char(18), MUNI_CODE_RIGHT char(18),
      OVERLAP_INDICATOR char(2), ROADWAY_CLASS number(2,0), STATE_CODE_LEFT string, STATE_CODE_RIGHT string, TAG_REVENUE_ELIGIBLE number(2,0), TWP_CODE_LEFT char(17), TWP_CODE_RIGHT char(17), NHS_CD char(2), NHS_INTERMODAL_ROUTE_CD number(3,0), OWNERSHIP_CD number(2,0), PRIORITY_SYSTEM_CD char(2), ROADWAY_WIDTH number(4,0), SEGMENT_DESCRIPTION_TXT char(33), SCENIC_BYWAY_CD string, SCENIC_ROUTE_NUMBER string, SHOULDER_TOTAL_WIDTH_LT number(3,0), SHOULDER_TOTAL_WIDTH_RT number(3,0), SHOULDER_PVD_WIDTH_IN_LT number(3,0), SHOULDER_PVD_WIDTH_IN_RT number(3,0), SHOULDER_PVD_WIDTH_OUT_LT number(3,0), SHOULDER_PVD_WIDTH_OUT_RT number(3,0), SHOULDER_TYPE_CD number(2,0), SPEED_LIMIT_NBR number(3,0), STREET_PREFIX_DIR_CD char(2), STREET_NAME char(22), STREET_SUFFIX_CD char(5), STREET_DIR_SUFFIX_CD string, SURFACE_TYPE_LEFT_CD char(2), SURFACE_TYPE_RIGHT_CD char(2), SURFACE_WIDTH_LEFT number(3,0),
      SURFACE_WIDTH_RIGHT number(3,0), LANES_NBR number(2,0), TRANSACTION_REASON_CODE char(2), TRANSACTION_COMMENT char(14), TRUCK_ROUTE_IND char(2), AREA_CODE_NBR number(6,0)
    -> AttributeManager
AttributeManager
    ATTR_TABLE = SET_TO FROMMEASURE = FME_CONDITIONAL:DEFAULT_VALUE'_FME_NO_OP_'BOOL_OP;OR;COMPOSITE_TEST;<Unused>;TEST @Value(FROMMEASURE) = -0.01'0'FME_NUM_CONDITIONS2___
    -> ChangeDetector_2 [REVISED]
ChangeDetector_2
    MATCH = 2D
    LENIENT_MATCH = No
    MATCH_STRATEGY = Match Selected Attributes
    BLANK_AND_MISSING_DIFFER = No
    MATCHATTRS = STREET_NAME TRANSACTION_COMMENT LANES_NBR SCENIC_ROUTE_NUMBER ACCESS_CONTROL_CD BASE_TYPE_RIGHT_CD SAMPLE_ID MUNI_CODE_RIGHT SURFACE_TYPE_LEFT_CD COUNTY_CODE_LEFT BASE_TYPE_LEFT_CD JURISDICTION STREET_PREFIX_DIR_CD TWP_CODE_RIGHT TOMEASURE ACCESS_CONTROL_OPNL_CD STREET_SUFFIX_CD STREET_DIR_SUFFIX_CD COUNTY_CODE_RIGHT NHS_CD MEDIAN_WIDTH_NBR SURFACE_WIDTH_RIGHT FAP_IND OWNERSHIP_CD SHOULDER_PVD_WIDTH_OUT_RT SHOULDER_TOTAL_WIDTH_LT ROADWAY_WIDTH NHS_INTERMODAL_ROUTE_CD TRANSACTION_REASON_CODE SHOULDER_TYPE_CD SURFACE_WIDTH_LEFT STATE_CODE_LEFT TAG_REVENUE_ELIGIBLE SHOULDER_PVD_WIDTH_IN_LT SHOULDER_PVD_WIDTH_IN_RT SPEED_LIMIT_NBR MUNI_CODE_LEFT FROMMEASURE TWP_CODE_LEFT SCENIC_BYWAY_CD SURFACE_TYPE_RIGHT_CD ROADWAY_CLASS SHOULDER_PVD_WIDTH_OUT_LT COUNTY_CODE OVERLAP_INDICATOR FACILITY_TYPE_CD COUNTY MILEAGE_CLASS DIRECTION_OF_TRAVEL_CD SEGMENT_DESCRIPTION_TXT FUNCTION_CLASS_CD LANE_WIDTH_NBR ROUTEID STATE_CODE_RIGHT DIVIDED_HWY_IND TRUCK_ROUTE_IND COUNTY_SPLIT_INDICATOR D_DISTRICT_ID SHOULDER_TOTAL_WIDTH_RT PRIORITY_SYSTEM_CD MAINTENANCE_AUTHORITY_CD MEDIAN_TYPE_CD AREA_CODE_NBR
    ADDED -> AttributeKeeper
    DELETED -> AttributeKeeper_2
AttributeKeeper
    KEEP_ATTRS = ROUTEID,SEGMENT_DESCRIPTION_TXT,FROMMEASURE,REENTER_IND,LEAVE_IND,TOMEASURE
    -> ChangeDetector_2_Added
ChangeDetector_2_Added: Inspector
AttributeKeeper_2
    KEEP_ATTRS = ROUTEID,SEGMENT_DESCRIPTION_TXT,FROMMEASURE,REENTER_IND,LEAVE_IND,TOMEASURE
    -> ChangeDetector_2_Deleted
ChangeDetector_2_Deleted: Inspector

Bookmark: de-aggregate segment description
AttributeRemover
    REMOVE_ATTRS = ID
    -> LrsMeasureVertexCreator [BeginVertexCreator_Input]
LrsMeasureVertexCreator
    _END_MEASURE = @Value(TOMEASURE)
    _BEGIN_MEASURE = @Value(FROMMEASURE)
    EndVertexCreator_Output -> LineCombiner
LineCombiner
    CONSIDER_NODE_ELEVATION = no
    TOPOLOGY = End noded
    ACCUM_ATTRS_NAME = Merge Incoming Attributes
    LINES_AS_SEGMENTS = No
    GROUP_BY = STREET_NAME TRANSACTION_COMMENT LANES_NBR SCENIC_ROUTE_NUMBER ACCESS_CONTROL_CD BASE_TYPE_RIGHT_CD SAMPLE_ID MUNI_CODE_RIGHT SURFACE_TYPE_LEFT_CD COUNTY_CODE_LEFT BASE_TYPE_LEFT_CD JURISDICTION STREET_PREFIX_DIR_CD TWP_CODE_RIGHT ACCESS_CONTROL_OPNL_CD STREET_SUFFIX_CD STREET_DIR_SUFFIX_CD REENTER_IND COUNTY_CODE_RIGHT NHS_CD MEDIAN_WIDTH_NBR SURFACE_WIDTH_RIGHT FAP_IND OWNERSHIP_CD SHOULDER_PVD_WIDTH_OUT_RT SHOULDER_TOTAL_WIDTH_LT ROADWAY_WIDTH NHS_INTERMODAL_ROUTE_CD TRANSACTION_REASON_CODE SHOULDER_TYPE_CD SURFACE_WIDTH_LEFT fme_feature_type STATE_CODE_LEFT TAG_REVENUE_ELIGIBLE SHOULDER_PVD_WIDTH_IN_LT SHOULDER_PVD_WIDTH_IN_RT SPEED_LIMIT_NBR MUNI_CODE_LEFT TWP_CODE_LEFT SCENIC_BYWAY_CD SURFACE_TYPE_RIGHT_CD ROADWAY_CLASS SHOULDER_PVD_WIDTH_OUT_LT COUNTY_CODE OVERLAP_INDICATOR FACILITY_TYPE_CD COUNTY MILEAGE_CLASS DIRECTION_OF_TRAVEL_CD FUNCTION_CLASS_CD LANE_WIDTH_NBR ROUTEID STATE_CODE_RIGHT DIVIDED_HWY_IND TRUCK_ROUTE_IND COUNTY_SPLIT_INDICATOR D_DISTRICT_ID SHOULDER_TOTAL_WIDTH_RT PRIORITY_SYSTEM_CD LEAVE_IND MAINTENANCE_AUTHORITY_CD MEDIAN_TYPE_CD AREA_CODE_NBR
    BREAK = no
    CONNECT_Z_MODE = First Wins
    PRESERVE = no
    LINE -> CoordinateExtractor
CoordinateExtractor
    IND = 0
    MODE = Specify Coordinate
    X_ATTR = FROMMEASURE
    -> CoordinateExtractor_2
CoordinateExtractor_2
    IND = -1
    MODE = Specify Coordinate
    X_ATTR = TOMEASURE
    -> GeometryRemover
GeometryRemover
    -> Tester_2
Tester_2
    TEST_MODE = Automatic
    TEST_DESCRIPTION = ""
    TEST_CLAUSE = TEST @Value(FROMMEASURE) != @Value(TOMEASURE)
    BOOL_OP = OR
    PASSED -> ChangeDetector_2 [ORIGINAL]

FME custom transformer LrsMeasureVertexCreator

Parameters:
- _BEGIN_MEASURE = @Value(_Begin_Measure)   # Begin Measure
- _END_MEASURE = @Value(_End_Measure)   # End Measure

BeginVertexCreator_Input (input)
    -> GeometryRemover
GeometryRemover
    -> BeginVertexCreator
BeginVertexCreator: VertexCreator
    MODE_NAME = Add Point
    XVAL = @Value(_Begin_Measure)
    YVAL = 0
    -> EndVertexCreator
EndVertexCreator: VertexCreator
    MODE_NAME = Add Point
    XVAL = @Value(_End_Measure)
    YVAL = 0
    -> AttributeManager
AttributeManager
    ATTR_TABLE:
      REMOVE _Begin_Measure
      REMOVE _End_Measure
    -> EndVertexCreator_Output (output)
EndVertexCreator_Output (output)
