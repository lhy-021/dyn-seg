FME workspace Dynamic Segmentation RIMS - FME Server.fmw

Readers:
- ORACLE_NONSPATIAL_1: ORACLE_NONSPATIAL from RIMS_TEST

Writers:
- SQLITE3_1: SQLITE3 to $(FME_MF_DIR)sde-export.sqlite

RH.LRSE_SURFACE_WIDTH (reader ORACLE_NONSPATIAL_1)
    attributes: OBJECTID number(38,0), SURFACE_WIDTH_ID nvarchar(38), NLF_ID nvarchar(14), MEASURE_FROM number(8,3), MEASURE_TO number(8,3), SURFACE_WIDTH_LEFT number(5,0), SURFACE_WIDTH_RIGHT number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_MILEAGE_ALLOCATION (reader ORACLE_NONSPATIAL_1)
    attributes: OBJECTID number(38,0), MILEAGE_ALLOCATION_ID nvarchar(38), NLF_ID nvarchar(14), MEASURE_FROM number(8,3), MEASURE_TO number(8,3), COUNTY_CODE nvarchar(3), COUNTY_CODE_LEFT nvarchar(3), COUNTY_CODE_RIGHT nvarchar(3), COUNTY_SPLIT_INDICATOR nvarchar(1), JURISDICTION nvarchar(1), MILEAGE_CLASS number(2,0), MUNI_CODE_LEFT nvarchar(50), MUNI_CODE_RIGHT nvarchar(50), OVERLAP_INDICATOR nvarchar(1), ROADWAY_CLASS number(2,0), STATE_CODE_LEFT nvarchar(2), STATE_CODE_RIGHT nvarchar(2), TAG_REVENUE_ELIGIBLE number(2,0), TWP_CODE_LEFT nvarchar(50), TWP_CODE_RIGHT nvarchar(50), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_ACCESS_CONTROL_OPNL (reader ORACLE_NONSPATIAL_1)
    attributes: OBJECTID number(38,0), ACCESS_CONTROL_OPNL_ID nvarchar(38), NLF_ID nvarchar(14), MEASURE_FROM number(8,3), MEASURE_TO number(8,3), ACCESS_CONTROL_OPNL_CD number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_SHOULDER_TYPE (reader ORACLE_NONSPATIAL_1)
    attributes: OBJECTID number(38,0), SHOULDER_TYPE_ID nvarchar(38), NLF_ID nvarchar(14), MEASURE_FROM number(8,3), MEASURE_TO number(8,3), SHOULDER_TYPE_CD number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_TRANSACTION_CODE (reader ORACLE_NONSPATIAL_1)
    attributes: OBJECTID number(38,0), TRANSACTION_REASON_ID nvarchar(38), NLF_ID nvarchar(14), MEASURE_FROM number(8,3), MEASURE_TO number(8,3), TRANSACTION_REASON_CODE nvarchar(1), TRANSACTION_COMMENT nvarchar(100), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_ACCESS_CONTROL_JRN (reader ORACLE_NONSPATIAL_1)
    attributes: OBJECTID number(38,0), ACCESS_CONTROL_ID nvarchar(38), NLF_ID nvarchar(14), MEASURE_FROM number(8,3), MEASURE_TO number(8,3), ACCESS_CONTROL_CD nvarchar(1), RH_DATE_ESTABLISH date, RH_DATE_RETIRE date, SYSTEM_DATE_CREATE date, SYSTEM_DATE_MOD date, USER_CREATE nvarchar(100), USER_MOD nvarchar(100), LOC_ORIG nvarchar(100), LOCERROR nvarchar(100)
    -> AttributeRounder_3
RH.LRSE_URBAN_AREA (reader ORACLE_NONSPATIAL_1)
    attributes: OBJECTID number(38,0), URBAN_AREA_ID nvarchar(38), NLF_ID nvarchar(14), MEASURE_FROM number(8,3), MEASURE_TO number(8,3), AREA_CODE_NBR nvarchar(9), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_OWNERSHIP (reader ORACLE_NONSPATIAL_1)
    attributes: OBJECTID number(38,0), OWNERSHIP_ID nvarchar(38), NLF_ID nvarchar(14), MEASURE_FROM number(8,3), MEASURE_TO number(8,3), OWNERSHIP_CD number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_SHOULDER_WIDTH (reader ORACLE_NONSPATIAL_1)
    attributes: OBJECTID number(38,0), SHOULDER_WIDTH_ID nvarchar(38), NLF_ID nvarchar(14), MEASURE_FROM number(8,3), MEASURE_TO number(8,3), SHOULDER_TOTAL_WIDTH_LT number(5,0), SHOULDER_TOTAL_WIDTH_RT number(5,0), SHOULDER_PVD_WIDTH_IN_LT number(5,0), SHOULDER_PVD_WIDTH_IN_RT number(5,0), SHOULDER_PVD_WIDTH_OUT_LT number(5,0), SHOULDER_PVD_WIDTH_OUT_RT number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_SURFACE_TYPE (reader ORACLE_NONSPATIAL_1)
    attributes: OBJECTID number(38,0), SURFACE_TYPE_ID nvarchar(38), NLF_ID nvarchar(14), MEASURE_FROM number(8,3), MEASURE_TO number(8,3), SURFACE_TYPE_LEFT_CD nvarchar(1), SURFACE_TYPE_RIGHT_CD nvarchar(1), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_SCENIC_ROUTE (reader ORACLE_NONSPATIAL_1)
    attributes: OBJECTID number(38,0), SCENIC_ROUTE_ID nvarchar(38), NLF_ID nvarchar(14), MEASURE_FROM number(8,3), MEASURE_TO number(8,3), SCENIC_BYWAY_CD nvarchar(1), SCENIC_ROUTE_NUMBER nvarchar(2), RH_DATE_ESTABLISH date, RH_DATE_RETIRE date, SYSTEM_DATE_CREATE date, SYSTEM_DATE_MOD date, USER_MOD nvarchar(100), USER_CREATE nvarchar(100), LOCERROR nvarchar(100)
    -> AttributeRounder_3
RH.LRSE_NHS (reader ORACLE_NONSPATIAL_1)
    attributes: OBJECTID number(38,0), NHS_ID nvarchar(38), NLF_ID nvarchar(14), MEASURE_FROM number(8,3), MEASURE_TO number(8,3), NHS_CD nvarchar(1), NHS_INTERMODAL_ROUTE_CD nvarchar(2), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_MAINTENANCE_AUTHORITY (reader ORACLE_NONSPATIAL_1)
    attributes: OBJECTID number(38,0), MAINTENANCE_AUTHORITY_ID nvarchar(38), NLF_ID nvarchar(14), MEASURE_FROM number(8,3), MEASURE_TO number(8,3), MAINTENANCE_AUTHORITY_CD number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_LANE_WIDTH (reader ORACLE_NONSPATIAL_1)
    attributes: OBJECTID number(38,0), LANE_WIDTH_ID nvarchar(38), NLF_ID nvarchar(14), MEASURE_FROM number(8,3), MEASURE_TO number(8,3), LANE_WIDTH_NBR number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_PRIORITY_SYSTEM (reader ORACLE_NONSPATIAL_1)
    attributes: OBJECTID number(38,0), PRIORITY_SYSTEM_ID nvarchar(38), NLF_ID nvarchar(14), MEASURE_FROM number(8,3), MEASURE_TO number(8,3), PRIORITY_SYSTEM_CD nvarchar(1), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_DIRECTION_OF_TRAVEL (reader ORACLE_NONSPATIAL_1)
    attributes: OBJECTID number(38,0), DIRECTION_OF_TRAVEL_ID nvarchar(38), NLF_ID nvarchar(14), MEASURE_FROM number(8,3), MEASURE_TO number(8,3), DIRECTION_OF_TRAVEL_CD nvarchar(1), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_MEDIAN_WIDTH (reader ORACLE_NONSPATIAL_1)
    attributes: OBJECTID number(38,0), MEDIAN_WIDTH_ID nvarchar(38), NLF_ID nvarchar(14), MEASURE_FROM number(8,3), MEASURE_TO number(8,3), MEDIAN_WIDTH_NBR number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_FUNCTIONAL_CLASS (reader ORACLE_NONSPATIAL_1)
    attributes: OBJECTID number(38,0), FUNCTIONAL_CLASS_ID nvarchar(38), NLF_ID nvarchar(14), MEASURE_FROM number(8,3), MEASURE_TO number(8,3), FUNCTION_CLASS_CD number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_THROUGH_LANES (reader ORACLE_NONSPATIAL_1)
    attributes: OBJECTID number(38,0), THROUGH_LANES_ID nvarchar(38), NLF_ID nvarchar(14), MEASURE_FROM number(8,3), MEASURE_TO number(8,3), LANES_NBR number(10,0), RH_DATE_ESTABLISH date, RH_DATE_RETIRE date, SYSTEM_DATE_CREATE date, SYSTEM_DATE_MOD date, USER_MOD nvarchar(100), USER_CREATE nvarchar(100), LOCERROR nvarchar(100)
    -> AttributeRounder_3
RH.LRSE_MEDIAN_TYPE (reader ORACLE_NONSPATIAL_1)
    attributes: OBJECTID number(38,0), MEDIAN_ID nvarchar(38), NLF_ID nvarchar(14), MEASURE_FROM number(8,3), MEASURE_TO number(8,3), MEDIAN_TYPE_CD number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_STREET_NAMES (reader ORACLE_NONSPATIAL_1)
    attributes: OBJECTID number(38,0), STREET_NAMES_ID nvarchar(38), NLF_ID nvarchar(14), MEASURE_FROM number(8,3), MEASURE_TO number(8,3), STREET_PREFIX_DIR_CD nvarchar(1), STREET_NAME nvarchar(100), STREET_SUFFIX_CD nvarchar(4), STREET_DIR_SUFFIX_CD nvarchar(2), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_HPMS_SAMPLE (reader ORACLE_NONSPATIAL_1)
    attributes: OBJECTID number(38,0), HPMS_EVENT_ID nvarchar(38), NLF_ID nvarchar(14), MEASURE_FROM number(8,3), MEASURE_TO number(8,3), BUSINESS_DATE date, T nvarchar(1), CO nvarchar(3), JURISDICTION nvarchar(1), ROUTE_TYPE nvarchar(2), ROUTE nvarchar(5), ROUTE_SUFFIX nvarchar(1), STATE_ROUTE_SUFFIX nvarchar(1), CARDINALITY nvarchar(1), SAMPLE_ID nvarchar(12), BEGIN_SAMPLE_DESCRIPTION nvarchar(255), END_SAMPLE_DESCRIPTION nvarchar(255), F_SYSTEM number(4,0), URBAN_CODE nvarchar(9), ACCESS_CONTROL number(4,0), FACILITY_TYPE number(4,0), SURFACE_TYPE number(5,0), THROUGH_LANES number(5,0), PEAK_LANES number(5,0), COUNTER_PEAK_LANES number(5,0), TURN_LANE_RIGHT number(4,0), TURN_LANE_LEFT number(4,0), PEAK_PARKING number(4,0), LANE_WIDTH number(5,0), SPEED_LIMIT number(4,0),
      AT_GRADE_OTHER number(5,0), STOP_SIGNS number(5,0), NUMBER_SIGNALS number(5,0), SIGNAL_TYPE number(4,0), PCT_GREEN_TIME number(5,0), SHOULDER_TYPE number(4,0), SHOULDER_WIDTH_R number(5,0), SHOULDER_WIDTH_L number(5,0), MEDIAN_TYPE number(4,0), MEDIAN_WIDTH number(5,0), PCT_PASS_SIGHT number(5,0), TERRAIN_TYPE number(5,0), WIDENING_OBSTACLE nvarchar(7), WIDENING_POTENTIAL number(5,0), PSR number(2,1), YEAR_LAST_IMPROVEMENT number(4,0), CURVES_A number(8,3), CURVES_B number(8,3), CURVES_C number(8,3), CURVES_D number(8,3), CURVES_E number(8,3), CURVES_F number(8,3), GRADES_A number(8,3), GRADES_B number(8,3), GRADES_C number(8,3), GRADES_D number(8,3), GRADES_E number(8,3), GRADES_F number(8,3), YEAR_REVIEWED number(4,0), DATE_CODED date,
      CODED_BY nvarchar(50), PROJECT_CODED date, REMARKS nvarchar(255), VOLUME_GROUP number(5,0), STD_EXP_FACTOR number(9,3), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_SPEED_LIMIT (reader ORACLE_NONSPATIAL_1)
    attributes: OBJECTID number(38,0), SPEED_LIMIT_ID nvarchar(38), NLF_ID nvarchar(14), MEASURE_FROM number(8,3), MEASURE_TO number(8,3), SPEED_LIMIT_NBR number(5,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_TRUCK_ROUTE (reader ORACLE_NONSPATIAL_1)
    attributes: OBJECTID number(38,0), TRUCK_ROUTE_ID nvarchar(38), NLF_ID nvarchar(14), MEASURE_FROM number(8,3), MEASURE_TO number(8,3), TRUCK_ROUTE_IND nvarchar(1), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_DIVIDED_HIGHWAY (reader ORACLE_NONSPATIAL_1)
    attributes: OBJECTID number(38,0), DIVIDED_HIGHWAY_ID nvarchar(38), NLF_ID nvarchar(14), MEASURE_FROM number(8,3), MEASURE_TO number(8,3), DIVIDED_HWY_IND nvarchar(1), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_DISTRICT (reader ORACLE_NONSPATIAL_1)
    attributes: OBJECTID number(38,0), DISTRICT_ID nvarchar(38), NLF_ID nvarchar(14), MEASURE_FROM number(8,3), MEASURE_TO number(8,3), D_DISTRICT_ID nvarchar(2), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_ROADWAY_WIDTH (reader ORACLE_NONSPATIAL_1)
    attributes: OBJECTID number(38,0), ROADWAY_WIDTH_ID nvarchar(38), NLF_ID nvarchar(14), MEASURE_FROM number(8,3), MEASURE_TO number(8,3), ROADWAY_WIDTH number(4,0), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_FACILITY_TYPE (reader ORACLE_NONSPATIAL_1)
    attributes: OBJECTID number(38,0), FACILITY_TYPE_ID nvarchar(38), NLF_ID nvarchar(14), MEASURE_FROM number(8,3), MEASURE_TO number(8,3), FACILITY_TYPE_CD number(5,0), RH_DATE_ESTABLISH date, RH_DATE_RETIRE date, SYSTEM_DATE_CREATE date, SYSTEM_DATE_MOD date, USER_MOD nvarchar(100), USER_CREATE nvarchar(100), LOCERROR nvarchar(100)
    -> AttributeRounder_3
RH.LRSE_BASE_TYPE (reader ORACLE_NONSPATIAL_1)
    attributes: OBJECTID number(38,0), BASE_TYPE_ID nvarchar(38), NLF_ID nvarchar(14), MEASURE_FROM number(8,3), MEASURE_TO number(8,3), BASE_TYPE_LEFT_CD nvarchar(1), BASE_TYPE_RIGHT_CD nvarchar(1), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_FEDERAL_AID_ROUTE (reader ORACLE_NONSPATIAL_1)
    attributes: OBJECTID number(38,0), FAP_ID nvarchar(38), NLF_ID nvarchar(14), MEASURE_FROM number(8,3), MEASURE_TO number(8,3), FAP_IND nvarchar(1), RH_DATE_ESTABLISH date, RH_DATE_RETIRE date, SYSTEM_DATE_CREATE date, SYSTEM_DATE_MOD date, USER_CREATE nvarchar(100), USER_MOD nvarchar(100), LOCERROR nvarchar(100)
    -> AttributeRounder_3
RH.LRSE_COUNTY (reader ORACLE_NONSPATIAL_1)
    attributes: OBJECTID number(38,0), COUNTY_ID nvarchar(38), NLF_ID nvarchar(14), MEASURE_FROM number(8,3), MEASURE_TO number(8,3), COUNTY nvarchar(3), RH_DATE_ESTABLISH date, RH_DATE_RETIRE date, SYSTEM_DATE_CREATE date, SYSTEM_DATE_MOD date, USER_CREATE nvarchar(100), USER_MOD nvarchar(100), LOCERROR nvarchar(100)
    -> AttributeRounder_3
Note: Segment Description attribute append
FeatureMerger
    GROUP_BY = NLF_ID
    JOIN_KEYS = @Value(NLF_ID) @Value(NLF_ID) AUTO @Value(MEASURE_FROM) @Value(MEASURE_FROM) AUTO
    SUPPLIERS_FIRST = No
    MERGE_TYPE = Attributes Only
    GEOM_TYPE = Build Polygons
    REJECT_NULL_MISSING_KEYS = No
    ATTR_CONFLICT_RES = Use Requestor
    IGNORE_NULLS = No
    PROCESS_DUPS = Yes
    ATTR_ACCUM_MODE = Merge Supplier
    CONNECT_Z_MODE = First Wins
    MERGED -> FeatureMerger_2 [REQUESTOR]
    UNMERGED_REQUESTOR -> FeatureMerger_2 [REQUESTOR]
Note: Reenter attribute append
FeatureMerger_2
    GROUP_BY = NLF_ID
    JOIN_KEYS = @Value(NLF_ID) @Value(NLF_ID) AUTO @Value(MEASURE_FROM) @Value(MEASURE_FROM) AUTO
    SUPPLIERS_FIRST = No
    MERGE_TYPE = Attributes Only
    GEOM_TYPE = Build Polygons
    REJECT_NULL_MISSING_KEYS = No
    ATTR_CONFLICT_RES = Use Requestor
    IGNORE_NULLS = No
    PROCESS_DUPS = Yes
    ATTR_ACCUM_MODE = Merge Supplier
    CONNECT_Z_MODE = First Wins
    MERGED -> FeatureMerger_3 [REQUESTOR]
    UNMERGED_REQUESTOR -> FeatureMerger_3 [REQUESTOR]
Note: Leave attribute append
FeatureMerger_3
    GROUP_BY = NLF_ID
    JOIN_KEYS = @Value(NLF_ID) @Value(NLF_ID) AUTO @Value(MEASURE_TO) @Value(MEASURE_TO) AUTO
    SUPPLIERS_FIRST = No
    MERGE_TYPE = Attributes Only
    GEOM_TYPE = Build Polygons
    REJECT_NULL_MISSING_KEYS = No
    ATTR_CONFLICT_RES = Use Requestor
    IGNORE_NULLS = No
    PROCESS_DUPS = Yes
    ATTR_ACCUM_MODE = Merge Supplier
    CONNECT_Z_MODE = First Wins
    MERGED -> NullAttributeMapper
    UNMERGED_REQUESTOR -> NullAttributeMapper
Note: Map Segment Description missing to null
NullAttributeMapper
    NULL_TREATMENT = Null
    ATTRLIST = SEGMENT_DESCRIPTION_TXT
    SOURCE_ATTR_VAL = Empty "Missing (Selected Attributes Only)" Null
    ATTRCHOICE = Selected Attributes
    -> NullAttributeMapper_2
Note: Map leave and reenter missing to N
NullAttributeMapper_2
    NULL_TREATMENT = New Value
    ATTRLIST = LEAVE_IND REENTER_IND
    SOURCE_ATTR_VAL = Empty "Missing (Selected Attributes Only)" Null
    ATTRCHOICE = Selected Attributes
    NEW_VALUE = N
    -> Tester_3
Note: Filter out zero length segments
Tester_3
    BOOL_OP = OR
    TEST_DESCRIPTION = ""
    TEST_MODE = Automatic
    TEST_CLAUSE = TEST @Value(MEASURE_FROM) != @Value(MEASURE_TO)
    PASSED -> mashup_all_FMEserver (writer SQLITE3_1)
mashup_all_FMEserver (writer SQLITE3_1)
    attributes: ID varchar(38), ROUTEID varchar(14), FROMMEASURE float, TOMEASURE float, ACCESS_CONTROL_CD varchar(1), ACCESS_CONTROL_OPNL_CD integer, BASE_TYPE_LEFT_CD varchar(1), BASE_TYPE_RIGHT_CD varchar(1), COUNTY varchar(3), DIRECTION_OF_TRAVEL_CD varchar(1), D_DISTRICT_ID varchar(2), DIVIDED_HWY_IND varchar(1), FACILITY_TYPE_CD integer, FAP_IND varchar(1), FUNCTION_CLASS_CD integer, SAMPLE_ID varchar(12), LANE_WIDTH_NBR integer, LEAVE_IND varchar(1), REENTER_IND varchar(1), MAINTENANCE_AUTHORITY_CD integer, MEDIAN_TYPE_CD integer, MEDIAN_WIDTH_NBR integer, COUNTY_CODE varchar(3), COUNTY_CODE_LEFT varchar(3), COUNTY_CODE_RIGHT varchar(3), COUNTY_SPLIT_INDICATOR varchar(1), JURISDICTION varchar(1), MILEAGE_CLASS integer, MUNI_CODE_LEFT varchar(50), MUNI_CODE_RIGHT varchar(50),
      OVERLAP_INDICATOR varchar(1), ROADWAY_CLASS integer, STATE_CODE_LEFT varchar(2), STATE_CODE_RIGHT varchar(2), TAG_REVENUE_ELIGIBLE integer, TWP_CODE_LEFT varchar(50), TWP_CODE_RIGHT varchar(50), NHS_CD varchar(1), NHS_INTERMODAL_ROUTE_CD varchar(2), OWNERSHIP_CD integer, PRIORITY_SYSTEM_CD varchar(1), ROADWAY_WIDTH integer, SEGMENT_DESCRIPTION_TXT varchar(255), SCENIC_BYWAY_CD varchar(1), SCENIC_ROUTE_NUMBER varchar(2), SHOULDER_TOTAL_WIDTH_LT integer, SHOULDER_TOTAL_WIDTH_RT integer, SHOULDER_PVD_WIDTH_IN_LT integer, SHOULDER_PVD_WIDTH_IN_RT integer, SHOULDER_PVD_WIDTH_OUT_LT integer, SHOULDER_PVD_WIDTH_OUT_RT integer, SHOULDER_TYPE_CD integer, SPEED_LIMIT_NBR integer, STREET_PREFIX_DIR_CD varchar(1), STREET_NAME varchar(100), STREET_SUFFIX_CD varchar(4), STREET_DIR_SUFFIX_CD varchar(2), SURFACE_TYPE_LEFT_CD varchar(1), SURFACE_TYPE_RIGHT_CD varchar(1), SURFACE_WIDTH_LEFT integer,
      SURFACE_WIDTH_RIGHT integer, LANES_NBR integer, TRANSACTION_REASON_CODE varchar(1), TRANSACTION_COMMENT varchar(100), TRUCK_ROUTE_IND varchar(1), AREA_CODE_NBR varchar(9)

Bookmark: SpatialOverlayer
AttributeRounder_3
    ROUND_TYPE = Nearest
    SRC_ATTRS = MEASURE_TO MEASURE_FROM
    PLACES = 3
    -> VertexCreator
Note: Replace geometry from measures
VertexCreator
    XVAL = @Value(MEASURE_FROM)
    YVAL = 0
    MODE_NAME = Replace with Point
    -> VertexCreator_2
VertexCreator_2
    XVAL = @Value(MEASURE_TO)
    YVAL = 0
    MODE_NAME = Add Point
    -> Sorter_2
Sorter_2
    SORT_PARM = NLF_ID ALPHA ASCENDING MEASURE_FROM NUMERIC ASCENDING
    SORTED -> LineOnLineOverlayer [LINE]
Note: Overlay measure geometry
LineOnLineOverlayer
    GROUP_BY = NLF_ID
    SEPARATE_COLLINEAR_SEGMENTS = No
    ATTRS_ACCUM_MODE = Merge Attributes
    DEAGGREGATE_INPUT = Yes
    GENERATE_LIST_DROP = NO
    LOG_LEVEL = Limited
    LINE -> PointOnLineOverlayer [LINE]
    <REJECTED> -> LineOnLineOverlayer__Rejected_
LineOnLineOverlayer__Rejected_: Inspector [off]
AttributeKeeper
    KEEP_ATTRS = NLF_ID
    -> Sorter_3
Sorter_3
    SORT_PARM = NLF_ID ALPHA ASCENDING
    SORTED -> PointOnLineOverlayer [POINT]
PointOnLineOverlayer
    GROUP_BY = NLF_ID
    DEAGGREGATE_INPUT = Yes
    TOLERANCE = 0
    ATTR_CONFLICT_RES = Use Original
    ATTR_ACCUM_MODE = Merge Incoming
    LINE -> CoordinateExtractor
    <REJECTED> -> PointOnLineOverlayer__Rejected_
Note: Extract new measures
CoordinateExtractor
    X_ATTR = MEASURE_FROM
    MODE = Specify Coordinate
    IND = 0
    -> CoordinateExtractor_2
CoordinateExtractor_2
    X_ATTR = MEASURE_TO
    MODE = Specify Coordinate
    IND = -1
    -> AttributeRounder_2
AttributeRounder_2
    ROUND_TYPE = Nearest
    SRC_ATTRS = MEASURE_TO MEASURE_FROM
    PLACES = 3
    -> FeatureMerger [REQUESTOR]
PointOnLineOverlayer__Rejected_: Inspector [off]

Bookmark: LEAVE REENTER
RH.LRSE_LEAVE_REENTER (reader ORACLE_NONSPATIAL_1)
    attributes: OBJECTID number(38,0), LEAVE_REENTER_ID nvarchar(38), NLF_ID nvarchar(14), MEASURE_FROM number(8,3), MEASURE_TO number(8,3), LEAVE_IND nvarchar(1), REENTER_IND nvarchar(1), RH_DATE_ESTABLISH date, RH_DATE_RETIRE date, SYSTEM_DATE_CREATE date, SYSTEM_DATE_MOD date, USER_CREATE nvarchar(100), USER_MOD nvarchar(100), LOCERROR nvarchar(100)
    -> AttributeRounder_4
AttributeRounder_4
    ROUND_TYPE = Nearest
    SRC_ATTRS = MEASURE_TO MEASURE_FROM
    PLACES = 3
    -> Tester
    -> Tester_2
Tester
    BOOL_OP = OR
    TEST_DESCRIPTION = ""
    TEST_MODE = Automatic
    TEST_CLAUSE = TEST @Value(REENTER_IND) = Y
    PASSED -> AttributeRemover_2
Note: Re-enter
AttributeRemover_2
    REMOVE_ATTRS = MEASURE_TO,LEAVE_IND
    -> VertexCreator_5
VertexCreator_5
    XVAL = @Value(MEASURE_FROM)
    YVAL = 0
    MODE_NAME = Replace with Point
    -> FeatureMerger_2 [SUPPLIER]
    -> AttributeKeeper
Tester_2
    BOOL_OP = OR
    TEST_DESCRIPTION = ""
    TEST_MODE = Automatic
    TEST_CLAUSE = TEST @Value(LEAVE_IND) = Y
    PASSED -> AttributeRemover_3
Note: Leave
AttributeRemover_3
    REMOVE_ATTRS = MEASURE_FROM,REENTER_IND
    -> VertexCreator_4
VertexCreator_4
    XVAL = @Value(MEASURE_TO)
    YVAL = 0
    MODE_NAME = Replace with Point
    -> FeatureMerger_3 [SUPPLIER]
    -> AttributeKeeper

Bookmark: LRSE SEGMENT DESCRIPTION
RH.LRSE_SEGMENT_DESCRIPTION (reader ORACLE_NONSPATIAL_1)
    attributes: OBJECTID number(38,0), SEGMENT_DESC_ID nvarchar(38), NLF_ID nvarchar(14), MEASURE_FROM number(8,3), MEASURE_TO number(8,3), SEGMENT_DESCRIPTION_TXT nvarchar(255), RH_DATE_ESTABLISH date, RH_DATE_RETIRE date, SYSTEM_DATE_CREATE date, SYSTEM_DATE_MOD date, USER_CREATE nvarchar(100), USER_MOD nvarchar(100), LOCERROR nvarchar(100)
    -> AttributeRounder
AttributeRounder
    ROUND_TYPE = Nearest
    SRC_ATTRS = MEASURE_TO MEASURE_FROM
    PLACES = 3
    -> AttributeRemover
AttributeRemover
    REMOVE_ATTRS = MEASURE_TO
    -> VertexCreator_3
VertexCreator_3
    XVAL = @Value(MEASURE_FROM)
    YVAL = 0
    MODE_NAME = Replace with Point
    -> FeatureMerger [SUPPLIER]
    -> AttributeKeeper

FME custom transformer SpatialOverlayer_2

Parameters:
- MEASURE_FROM = @Value(MEASURE_FROM)   # Measure From
- NLF_ID = @Value(NLF_ID)   # Nlf Id
- MEASURE_TO = @Value(MEASURE_TO)   # Measure To

Bookmark: SpatialOverlayer
Sorter_2_Input_1 (input)
    -> Sorter_2
Sorter_2
    SORT_PARM = NLF_ID ALPHA ASCENDING MEASURE_FROM NUMERIC ASCENDING MEASURE_TO NUMERIC ASCENDING
    SORTED -> VertexCreator
Note: Replace geometry from measures
VertexCreator
    XVAL = @Value(MEASURE_FROM)
    YVAL = 0
    MODE_NAME = Replace with Point
    -> VertexCreator_2
VertexCreator_2
    XVAL = @Value(MEASURE_TO)
    YVAL = 0
    MODE_NAME = Add Point
    -> LineOnLineOverlayer [LINE]
Note: Overlay measure geometry
LineOnLineOverlayer
    GROUP_BY = NLF_ID
    SEPARATE_COLLINEAR_SEGMENTS = No
    ATTRS_ACCUM_MODE = Merge Attributes
    DEAGGREGATE_INPUT = Yes
    GENERATE_LIST_DROP = NO
    LOG_LEVEL = Full
    LINE -> CoordinateExtractor
Note: Extract new measures
CoordinateExtractor
    X_ATTR = MEASURE_FROM
    MODE = Specify Coordinate
    IND = 0
    -> CoordinateExtractor_2
CoordinateExtractor_2
    X_ATTR = MEASURE_TO
    MODE = Specify Coordinate
    IND = 1
    -> Sorter
Sorter
    SORT_PARM = NLF_ID ALPHA ASCENDING MEASURE_FROM NUMERIC ASCENDING MEASURE_TO NUMERIC ASCENDING
    SORTED -> Sorter_Sorted_1 (output)
Sorter_Sorted_1 (output)
