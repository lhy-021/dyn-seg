FME workspace Dynamic Segmentation RIMS.fmw

Parameters:
- TEXT = RH_DATE_RETIRE is null and SUBSTR(NLF_ID,2,3) = 'FRA'   # Filter_for_input_tables Filter for input tables

Readers:
- GEODATABASE_SDE_1: GEODATABASE_SDE
- GEODATABASE_SDE_2: GEODATABASE_SDE

Writers:
- FILEGDB_2: FILEGDB to $(FME_MF_DIR)RI.gdb

LineCombiner
    CONNECT_Z_MODE = First Wins
    TOPOLOGY = End noded
    GROUP_BY = COUNTY_CODE_RIGHT SURFACE_TYPE_RIGHT_CD SCENIC_BYWAY_CD SHOULDER_PVD_WIDTH_OUT_LT SHOULDER_PVD_WIDTH_OUT_RT ROADWAY_WIDTH NHS_INTERMODAL_ROUTE_CD STREET_PREFIX_DIR_CD FACILITY_TYPE_CD MEDIAN_WIDTH_NBR D_DISTRICT_ID FAP_IND BASE_TYPE_RIGHT_CD BASE_TYPE_LEFT_CD SEGMENT_DESCRIPTION_TXT SHOULDER_PVD_WIDTH_IN_RT OWNERSHIP_CD ACCESS_CONTROL_CD fme_feature_type SHOULDER_TYPE_CD SAMPLE_ID SURFACE_WIDTH_RIGHT TWP_CODE_LEFT SHOULDER_TOTAL_WIDTH_LT SHOULDER_PVD_WIDTH_IN_LT STATE_CODE_RIGHT RIGHT_POPULATION COUNTY COUNTY_CODE_LEFT STATE_CODE_LEFT MEDIAN_TYPE_CD MAINTENANCE_AUTHORITY_CD MUNI_CODE_LEFT TAG_REVENUE_ELIGIBLE STREET_DIR_SUFFIX_CD REENTER_IND LANE_WIDTH_NBR STREET_SUFFIX_CD OVERLAP_INDICATOR SCENIC_ROUTE_NUMBER SPEED_LIMIT_NBR ROUTE_SUFFIX RIGHT_FIPS_CODE JURISDICTION LEAVE_IND LANES_NBR ROUTE DIRECTION_OF_TRAVEL_CD _timestamp COUNTY_SPLIT_INDICATOR ROUTE_TYPE ROADWAY_CLASS PRIORITY_SYSTEM_CD AREA_CODE_NBR SURFACE_TYPE_LEFT_CD FUNCTION_CLASS_CD TWP_CODE_RIGHT LEFT_POPULATION MUNI_CODE_RIGHT STREET_NAME TRANSACTION_REASON_CODE TRUCK_ROUTE_IND ACCESS_CONTROL_OPNL_CD NLF_ID COUNTY_CODE DIVIDED_HWY_IND NHS_CD LEFT_FIPS_CODE SURFACE_WIDTH_LEFT MILEAGE_CLASS SHOULDER_TOTAL_WIDTH_RT
    CONSIDER_NODE_ELEVATION = no
    PRESERVE = no
    ACCUM_ATTRS_NAME = Use Attributes From One Feature
    LINES_AS_SEGMENTS = No
    BREAK = no
    LINE -> CoordinateExtractor_3
CoordinateExtractor_3
    MODE = Specify Coordinate
    X_ATTR = MEASURE_FROM
    IND = 0
    -> CoordinateExtractor_4
CoordinateExtractor_4
    MODE = Specify Coordinate
    X_ATTR = MEASURE_TO
    IND = -1
    -> GeometryRemover
FME_RI_events (writer FILEGDB_2)
    attributes: MUNI_CODE_LEFT text(50), SHOULDER_PVD_WIDTH_OUT_LT smallint, LEFT_POPULATION text(200), SCENIC_BYWAY_CD text(1), AREA_CODE_NBR text(9), TRANSACTION_REASON_CODE text(1), SURFACE_WIDTH_RIGHT smallint, TWP_CODE_RIGHT text(50), ROADWAY_CLASS smallint, SAMPLE_ID text(12), SHOULDER_TOTAL_WIDTH_RT smallint, FROMMEASURE text(200), STATE_CODE_RIGHT text(2), SHOULDER_TOTAL_WIDTH_LT smallint, SURFACE_TYPE_LEFT_CD text(1), MILEAGE_CLASS smallint, SHOULDER_PVD_WIDTH_IN_LT smallint, LANES_NBR int, SHOULDER_PVD_WIDTH_OUT_RT smallint, LEAVE_IND text(1), REENTER_IND text(1), SHOULDER_TYPE_CD smallint, COUNTY_CODE_RIGHT text(3), OWNERSHIP_CD smallint, STREET_DIR_SUFFIX_CD text(2), TAG_REVENUE_ELIGIBLE smallint, JURISDICTION text(1), DIVIDED_HWY_IND text(1), SURFACE_WIDTH_LEFT smallint, STREET_PREFIX_DIR_CD text(1),
      OVERLAP_INDICATOR text(1), ACCESS_CONTROL_OPNL_CD smallint, MEDIAN_WIDTH_NBR smallint, ACCESS_CONTROL_CD text(1), LANE_WIDTH_NBR smallint, FACILITY_TYPE_CD smallint, MAINTENANCE_AUTHORITY_CD smallint, ROUTEID text(200), BASE_TYPE_LEFT_CD text(1), MEDIAN_TYPE_CD smallint, NHS_CD text(1), COUNTY_CODE_LEFT text(3), FUNCTION_CLASS_CD smallint, FAP_IND text(1), ROUTE_TYPE text(2), TOMEASURE text(200), ROUTE text(5), STREET_NAME text(100), ROADWAY_WIDTH smallint, MUNI_CODE_RIGHT text(50), STATE_CODE_LEFT text(2), D_DISTRICT_ID text(2), RIGHT_POPULATION text(200), SCENIC_ROUTE_NUMBER text(2), SPEED_LIMIT_NBR smallint, TWP_CODE_LEFT text(50), SURFACE_TYPE_RIGHT_CD text(1), BASE_TYPE_RIGHT_CD text(1), DIRECTION_OF_TRAVEL_CD text(1), TRUCK_ROUTE_IND text(1),
      ROUTE_SUFFIX text(1), PRIORITY_SYSTEM_CD text(1), STREET_SUFFIX_CD text(4), COUNTY_SPLIT_INDICATOR text(1), COUNTY text(3), NHS_INTERMODAL_ROUTE_CD text(2), SEGMENT_DESCRIPTION_TXT text(255), SHOULDER_PVD_WIDTH_IN_RT smallint, COUNTY_CODE text(3)

Bookmark: Incoming data - Line features
RH.LRSE_MAINTENANCE_AUTHORITY (reader GEODATABASE_SDE_1)
    attributes: OBJECTID integer, MAINTENANCE_AUTHORITY_ID char(38), NLF_ID char(14), MEASURE_FROM double, MEASURE_TO double, MAINTENANCE_AUTHORITY_CD smallint, RH_DATE_ESTABLISH date, RH_DATE_RETIRE date, SYSTEM_DATE_CREATE date, SYSTEM_DATE_MOD date, USER_CREATE char(100), USER_MOD char(100), LOCERROR char(100), SHAPE.LEN double
    -> Junction_7
Junction_7
    -> Junction_8
RH.LRSE_FEDERAL_AID_ROUTE (reader GEODATABASE_SDE_1)
    attributes: OBJECTID integer, FAP_ID char(38), NLF_ID char(14), MEASURE_FROM double, MEASURE_TO double, FAP_IND char(1), RH_DATE_ESTABLISH date, RH_DATE_RETIRE date, SYSTEM_DATE_CREATE date, SYSTEM_DATE_MOD date, USER_CREATE char(100), USER_MOD char(100), LOCERROR char(100), SHAPE.LEN double
    -> Junction
Junction
    -> Junction_2
RH.LRSE_LANE_WIDTH (reader GEODATABASE_SDE_1)
    attributes: OBJECTID integer, LANE_WIDTH_ID char(38), NLF_ID char(14), MEASURE_FROM double, MEASURE_TO double, LANE_WIDTH_NBR smallint, RH_DATE_ESTABLISH date, RH_DATE_RETIRE date, SYSTEM_DATE_CREATE date, SYSTEM_DATE_MOD date, USER_CREATE char(100), USER_MOD char(100), LOCERROR char(100), SHAPE.LEN double
    -> Junction_9
Junction_9
    -> Junction_10
RH.LRSE_COUNTY (reader GEODATABASE_SDE_1)
    attributes: OBJECTID integer, COUNTY_ID char(38), NLF_ID char(14), MEASURE_FROM double, MEASURE_TO double, COUNTY char(3), RH_DATE_ESTABLISH date, RH_DATE_RETIRE date, SYSTEM_DATE_CREATE date, SYSTEM_DATE_MOD date, USER_CREATE char(100), USER_MOD char(100), LOCERROR char(100), SHAPE.LEN double
    -> Junction_3
Junction_3
    -> Junction_4
RH.LRSE_NHS (reader GEODATABASE_SDE_1)
    attributes: OBJECTID integer, NHS_ID char(38), NLF_ID char(14), MEASURE_FROM double, MEASURE_TO double, NHS_CD char(1), NHS_INTERMODAL_ROUTE_CD char(2), RH_DATE_ESTABLISH date, RH_DATE_RETIRE date, SYSTEM_DATE_CREATE date, SYSTEM_DATE_MOD date, USER_CREATE char(100), USER_MOD char(100), LOCERROR char(100), SHAPE.LEN double
    -> Junction_5
Junction_5
    -> Junction_6
RH.LRSE_PRIORITY_SYSTEM (reader GEODATABASE_SDE_1)
    attributes: OBJECTID integer, PRIORITY_SYSTEM_ID char(38), NLF_ID char(14), MEASURE_FROM double, MEASURE_TO double, PRIORITY_SYSTEM_CD char(1), RH_DATE_ESTABLISH date, RH_DATE_RETIRE date, SYSTEM_DATE_CREATE date, SYSTEM_DATE_MOD date, USER_CREATE char(100), USER_MOD char(100), LOCERROR char(100), SHAPE.LEN double
    -> Junction_11
Junction_11
    -> Junction_12
RH.LRSE_DIRECTION_OF_TRAVEL (reader GEODATABASE_SDE_1)
    attributes: OBJECTID integer, DIRECTION_OF_TRAVEL_ID char(38), NLF_ID char(14), MEASURE_FROM double, MEASURE_TO double, DIRECTION_OF_TRAVEL_CD char(1), RH_DATE_ESTABLISH date, RH_DATE_RETIRE date, SYSTEM_DATE_CREATE date, SYSTEM_DATE_MOD date, USER_CREATE char(100), USER_MOD char(100), LOCERROR char(100), SHAPE.LEN double
    -> Junction_13
Junction_13
    -> Junction_14
RH.LRSE_MEDIAN_WIDTH (reader GEODATABASE_SDE_1)
    attributes: OBJECTID integer, MEDIAN_WIDTH_ID char(38), NLF_ID char(14), MEASURE_FROM double, MEASURE_TO double, MEDIAN_WIDTH_NBR smallint, RH_DATE_ESTABLISH date, RH_DATE_RETIRE date, SYSTEM_DATE_CREATE date, SYSTEM_DATE_MOD date, USER_CREATE char(100), USER_MOD char(100), LOCERROR char(100), SHAPE.LEN double
    -> Junction_15
Junction_15
    -> Junction_16
RH.LRSE_FUNCTIONAL_CLASS (reader GEODATABASE_SDE_1)
    attributes: OBJECTID integer, FUNCTIONAL_CLASS_ID char(38), NLF_ID char(14), MEASURE_FROM double, MEASURE_TO double, FUNCTION_CLASS_CD smallint, RH_DATE_ESTABLISH date, RH_DATE_RETIRE date, SYSTEM_DATE_CREATE date, SYSTEM_DATE_MOD date, USER_CREATE char(100), USER_MOD char(100), LOCERROR char(100), SHAPE.LEN double
    -> Junction_17
Junction_17
    -> Junction_18
RH.LRSE_ACCESS_CONTROL_OPNL (reader GEODATABASE_SDE_1)
    attributes: OBJECTID integer, ACCESS_CONTROL_OPNL_ID char(38), NLF_ID char(14), MEASURE_FROM double, MEASURE_TO double, ACCESS_CONTROL_OPNL_CD smallint, RH_DATE_ESTABLISH date, RH_DATE_RETIRE date, SYSTEM_DATE_CREATE date, SYSTEM_DATE_MOD date, USER_CREATE char(100), USER_MOD char(100), LOCERROR char(100), SHAPE.LEN double
    -> Junction_19
Junction_19
    -> Junction_20
RH.LRSE_SHOULDER_TYPE (reader GEODATABASE_SDE_1)
    attributes: OBJECTID integer, SHOULDER_TYPE_ID char(38), NLF_ID char(14), MEASURE_FROM double, MEASURE_TO double, SHOULDER_TYPE_CD smallint, RH_DATE_ESTABLISH date, RH_DATE_RETIRE date, SYSTEM_DATE_CREATE date, SYSTEM_DATE_MOD date, USER_CREATE char(100), USER_MOD char(100), LOCERROR char(100), SHAPE.LEN double
    -> Junction_27
Junction_27
    -> Junction_28
RH.LRSE_OWNERSHIP (reader GEODATABASE_SDE_1)
    attributes: OBJECTID integer, OWNERSHIP_ID char(38), NLF_ID char(14), MEASURE_FROM double, MEASURE_TO double, OWNERSHIP_CD smallint, RH_DATE_ESTABLISH date, RH_DATE_RETIRE date, SYSTEM_DATE_CREATE date, SYSTEM_DATE_MOD date, USER_CREATE char(100), USER_MOD char(100), LOCERROR char(100), SHAPE.LEN double
    -> Junction_21
Junction_21
    -> Junction_22
RH.LRSE_THROUGH_LANES (reader GEODATABASE_SDE_1)
    attributes: OBJECTID integer, THROUGH_LANES_ID char(38), NLF_ID char(14), MEASURE_FROM double, MEASURE_TO double, LANES_NBR integer, RH_DATE_ESTABLISH date, RH_DATE_RETIRE date, SYSTEM_DATE_CREATE date, SYSTEM_DATE_MOD date, USER_MOD char(100), USER_CREATE char(100), LOCERROR char(100), SHAPE.LEN double
    -> Junction_23
Junction_23
    -> Junction_24
RH.LRSE_MEDIAN_TYPE (reader GEODATABASE_SDE_1)
    attributes: OBJECTID integer, MEDIAN_ID char(38), NLF_ID char(14), MEASURE_FROM double, MEASURE_TO double, MEDIAN_TYPE_CD smallint, RH_DATE_ESTABLISH date, RH_DATE_RETIRE date, SYSTEM_DATE_CREATE date, SYSTEM_DATE_MOD date, USER_CREATE char(100), USER_MOD char(100), LOCERROR char(100), SHAPE.LEN double
    -> Junction_25
Junction_25
    -> Junction_26
RH.LRSE_STREET_NAMES (reader GEODATABASE_SDE_1)
    attributes: OBJECTID integer, STREET_NAMES_ID char(38), NLF_ID char(14), MEASURE_FROM double, MEASURE_TO double, STREET_PREFIX_DIR_CD char(1), STREET_NAME char(100), STREET_SUFFIX_CD char(4), STREET_DIR_SUFFIX_CD char(2), RH_DATE_ESTABLISH date, RH_DATE_RETIRE date, SYSTEM_DATE_CREATE date, SYSTEM_DATE_MOD date, USER_CREATE char(100), USER_MOD char(100), LOCERROR char(100), SHAPE.LEN double
    -> Junction_29
Junction_29
    -> Junction_30
RH.LRSE_TRANSACTION_CODE (reader GEODATABASE_SDE_1)
    attributes: OBJECTID integer, TRANSACTION_REASON_ID char(38), NLF_ID char(14), MEASURE_FROM double, MEASURE_TO double, TRANSACTION_REASON_CODE char(1), TRANSACTION_COMMENT char(100), RH_DATE_ESTABLISH date, RH_DATE_RETIRE date, SYSTEM_DATE_CREATE date, SYSTEM_DATE_MOD date, USER_CREATE char(100), USER_MOD char(100), LOCERROR char(100), SHAPE.LEN double
    -> Junction_31
Junction_31
    -> Junction_32
RH.LRSE_ACCESS_CONTROL_JRN (reader GEODATABASE_SDE_1)
    attributes: OBJECTID integer, ACCESS_CONTROL_ID char(38), NLF_ID char(14), MEASURE_FROM double, MEASURE_TO double, ACCESS_CONTROL_CD char(1), RH_DATE_ESTABLISH date, RH_DATE_RETIRE date, SYSTEM_DATE_CREATE date, SYSTEM_DATE_MOD date, USER_CREATE char(100), USER_MOD char(100), LOC_ORIG char(100), LOCERROR char(100), SHAPE.LEN double
    -> Junction_33
Junction_33
    -> Junction_34
RH.LRSE_HPMS_SAMPLE (reader GEODATABASE_SDE_1)
    attributes: OBJECTID integer, HPMS_EVENT_ID char(38), NLF_ID char(14), MEASURE_FROM double, MEASURE_TO double, BUSINESS_DATE date, T char(1), CO char(3), JURISDICTION char(1), ROUTE_TYPE char(2), ROUTE char(5), ROUTE_SUFFIX char(1), STATE_ROUTE_SUFFIX char(1), CARDINALITY char(1), SAMPLE_ID char(12), BEGIN_SAMPLE_DESCRIPTION char(255), END_SAMPLE_DESCRIPTION char(255), F_SYSTEM smallint, URBAN_CODE char(9), ACCESS_CONTROL smallint, FACILITY_TYPE smallint, SURFACE_TYPE integer, THROUGH_LANES integer, PEAK_LANES integer, COUNTER_PEAK_LANES integer, TURN_LANE_RIGHT smallint, TURN_LANE_LEFT smallint, PEAK_PARKING smallint, LANE_WIDTH integer, SPEED_LIMIT smallint,
      AT_GRADE_OTHER integer, STOP_SIGNS integer, NUMBER_SIGNALS integer, SIGNAL_TYPE smallint, PCT_GREEN_TIME integer, SHOULDER_TYPE smallint, SHOULDER_WIDTH_R integer, SHOULDER_WIDTH_L integer, MEDIAN_TYPE smallint, MEDIAN_WIDTH integer, PCT_PASS_SIGHT integer, TERRAIN_TYPE integer, WIDENING_OBSTACLE char(7), WIDENING_POTENTIAL integer, PSR float, YEAR_LAST_IMPROVEMENT smallint, CURVES_A double, CURVES_B double, CURVES_C double, CURVES_D double, CURVES_E double, CURVES_F double, GRADES_A double, GRADES_B double, GRADES_C double, GRADES_D double, GRADES_E double, GRADES_F double, YEAR_REVIEWED smallint, DATE_CODED date,
      CODED_BY char(50), PROJECT_CODED date, REMARKS char(255), VOLUME_GROUP integer, STD_EXP_FACTOR double, RH_DATE_ESTABLISH date, RH_DATE_RETIRE date, SYSTEM_DATE_CREATE date, SYSTEM_DATE_MOD date, USER_CREATE char(100), USER_MOD char(100), LOCERROR char(100), SHAPE.LEN double
    -> Junction_35
Junction_35
    -> Junction_36
RH.LRSE_SHOULDER_WIDTH (reader GEODATABASE_SDE_1)
    attributes: OBJECTID integer, SHOULDER_WIDTH_ID char(38), NLF_ID char(14), MEASURE_FROM double, MEASURE_TO double, SHOULDER_TOTAL_WIDTH_LT smallint, SHOULDER_TOTAL_WIDTH_RT smallint, SHOULDER_PVD_WIDTH_IN_LT smallint, SHOULDER_PVD_WIDTH_IN_RT smallint, SHOULDER_PVD_WIDTH_OUT_LT smallint, SHOULDER_PVD_WIDTH_OUT_RT smallint, RH_DATE_ESTABLISH date, RH_DATE_RETIRE date, SYSTEM_DATE_CREATE date, SYSTEM_DATE_MOD date, USER_CREATE char(100), USER_MOD char(100), LOCERROR char(100), SHAPE.LEN double
    -> Junction_37
Junction_37
    -> Junction_38
RH.LRSE_SPEED_LIMIT (reader GEODATABASE_SDE_1)
    attributes: OBJECTID integer, SPEED_LIMIT_ID char(38), NLF_ID char(14), MEASURE_FROM double, MEASURE_TO double, SPEED_LIMIT_NBR smallint, RH_DATE_ESTABLISH date, RH_DATE_RETIRE date, SYSTEM_DATE_CREATE date, SYSTEM_DATE_MOD date, USER_CREATE char(100), USER_MOD char(100), LOCERROR char(100), SHAPE.LEN double
    -> Junction_39
Junction_39
    -> Junction_40
RH.LRSE_TRUCK_ROUTE (reader GEODATABASE_SDE_1)
    attributes: OBJECTID integer, TRUCK_ROUTE_ID char(38), NLF_ID char(14), MEASURE_FROM double, MEASURE_TO double, TRUCK_ROUTE_IND char(1), RH_DATE_ESTABLISH date, RH_DATE_RETIRE date, SYSTEM_DATE_CREATE date, SYSTEM_DATE_MOD date, USER_CREATE char(100), USER_MOD char(100), LOCERROR char(100), SHAPE.LEN double
    -> Junction_41
Junction_41
    -> Junction_42
RH.LRSE_DIVIDED_HIGHWAY (reader GEODATABASE_SDE_1)
    attributes: OBJECTID integer, DIVIDED_HIGHWAY_ID char(38), NLF_ID char(14), MEASURE_FROM double, MEASURE_TO double, DIVIDED_HWY_IND char(1), RH_DATE_ESTABLISH date, RH_DATE_RETIRE date, SYSTEM_DATE_CREATE date, SYSTEM_DATE_MOD date, USER_CREATE char(100), USER_MOD char(100), LOCERROR char(100), SHAPE.LEN double
    -> Junction_43
Junction_43
    -> Junction_44
RH.LRSE_URBAN_AREA (reader GEODATABASE_SDE_1)
    attributes: OBJECTID integer, URBAN_AREA_ID char(38), NLF_ID char(14), MEASURE_FROM double, MEASURE_TO double, AREA_CODE_NBR char(9), RH_DATE_ESTABLISH date, RH_DATE_RETIRE date, SYSTEM_DATE_CREATE date, SYSTEM_DATE_MOD date, USER_CREATE char(100), USER_MOD char(100), LOCERROR char(100), SHAPE.LEN double
    -> Junction_45
Junction_45
    -> Junction_46
RH.LRSE_DISTRICT (reader GEODATABASE_SDE_1)
    attributes: OBJECTID integer, DISTRICT_ID char(38), NLF_ID char(14), MEASURE_FROM double, MEASURE_TO double, D_DISTRICT_ID char(2), RH_DATE_ESTABLISH date, RH_DATE_RETIRE date, SYSTEM_DATE_CREATE date, SYSTEM_DATE_MOD date, USER_CREATE char(100), USER_MOD char(100), LOCERROR char(100), SHAPE.LEN double
    -> Junction_47
Junction_47
    -> Junction_48
RH.LRSE_ROADWAY_WIDTH (reader GEODATABASE_SDE_1)
    attributes: OBJECTID integer, ROADWAY_WIDTH_ID char(38), NLF_ID char(14), MEASURE_FROM double, MEASURE_TO double, ROADWAY_WIDTH smallint, RH_DATE_ESTABLISH date, RH_DATE_RETIRE date, SYSTEM_DATE_CREATE date, SYSTEM_DATE_MOD date, USER_CREATE char(100), USER_MOD char(100), LOCERROR char(100), SHAPE.LEN double
    -> Junction_49
Junction_49
    -> Junction_50
RH.LRSE_FACILITY_TYPE (reader GEODATABASE_SDE_1)
    attributes: OBJECTID integer, FACILITY_TYPE_ID char(38), NLF_ID char(14), MEASURE_FROM double, MEASURE_TO double, FACILITY_TYPE_CD smallint, RH_DATE_ESTABLISH date, RH_DATE_RETIRE date, SYSTEM_DATE_CREATE date, SYSTEM_DATE_MOD date, USER_MOD char(100), USER_CREATE char(100), LOCERROR char(100), SHAPE.LEN double
    -> Junction_51
Junction_51
    -> Junction_52
RH.LRSE_BASE_TYPE (reader GEODATABASE_SDE_1)
    attributes: OBJECTID integer, BASE_TYPE_ID char(38), NLF_ID char(14), MEASURE_FROM double, MEASURE_TO double, BASE_TYPE_LEFT_CD char(1), BASE_TYPE_RIGHT_CD char(1), RH_DATE_ESTABLISH date, RH_DATE_RETIRE date, SYSTEM_DATE_CREATE date, SYSTEM_DATE_MOD date, USER_CREATE char(100), USER_MOD char(100), LOCERROR char(100), SHAPE.LEN double
    -> Junction_53
Junction_53
    -> Junction_54
RH.LRSE_SURFACE_WIDTH (reader GEODATABASE_SDE_1)
    attributes: OBJECTID integer, SURFACE_WIDTH_ID char(38), NLF_ID char(14), MEASURE_FROM double, MEASURE_TO double, SURFACE_WIDTH_LEFT smallint, SURFACE_WIDTH_RIGHT smallint, RH_DATE_ESTABLISH date, RH_DATE_RETIRE date, SYSTEM_DATE_CREATE date, SYSTEM_DATE_MOD date, USER_CREATE char(100), USER_MOD char(100), LOCERROR char(100), SHAPE.LEN double
    -> Junction_55
Junction_55
    -> Junction_56
RH.LRSE_SURFACE_TYPE (reader GEODATABASE_SDE_1)
    attributes: OBJECTID integer, SURFACE_TYPE_ID char(38), NLF_ID char(14), MEASURE_FROM double, MEASURE_TO double, SURFACE_TYPE_LEFT_CD char(1), SURFACE_TYPE_RIGHT_CD char(1), RH_DATE_ESTABLISH date, RH_DATE_RETIRE date, SYSTEM_DATE_CREATE date, SYSTEM_DATE_MOD date, USER_CREATE char(100), USER_MOD char(100), LOCERROR char(100), SHAPE.LEN double
    -> Junction_57
Junction_57
    -> Junction_58
RH.LRSE_MILEAGE_ALLOCATION (reader GEODATABASE_SDE_1)
    attributes: OBJECTID integer, MILEAGE_ALLOCATION_ID char(38), NLF_ID char(14), MEASURE_FROM double, MEASURE_TO double, COUNTY_CODE char(3), COUNTY_CODE_LEFT char(3), COUNTY_CODE_RIGHT char(3), COUNTY_SPLIT_INDICATOR char(1), JURISDICTION char(1), MILEAGE_CLASS smallint, MUNI_CODE_LEFT char(50), MUNI_CODE_RIGHT char(50), OVERLAP_INDICATOR char(1), ROADWAY_CLASS smallint, STATE_CODE_LEFT char(2), STATE_CODE_RIGHT char(2), TAG_REVENUE_ELIGIBLE smallint, TWP_CODE_LEFT char(50), TWP_CODE_RIGHT char(50), RH_DATE_ESTABLISH date, RH_DATE_RETIRE date, SYSTEM_DATE_CREATE date, SYSTEM_DATE_MOD date, USER_CREATE char(100), USER_MOD char(100), LOCERROR char(100), SHAPE.LEN double
    -> Junction_61
Junction_61
    -> Junction_62
RH.LRSE_SCENIC_ROUTE (reader GEODATABASE_SDE_1)
    attributes: OBJECTID integer, SCENIC_ROUTE_ID char(38), NLF_ID char(14), MEASURE_FROM double, MEASURE_TO double, SCENIC_BYWAY_CD char(1), SCENIC_ROUTE_NUMBER char(2), RH_DATE_ESTABLISH date, RH_DATE_RETIRE date, SYSTEM_DATE_CREATE date, SYSTEM_DATE_MOD date, USER_MOD char(100), USER_CREATE char(100), LOCERROR char(100), SHAPE.LEN double
    -> Junction_59
Junction_59
    -> Junction_60

Bookmark: Incoming data prep
Junction_8
    -> AttributeRounder_3
Junction_2
    -> AttributeRounder_3
Junction_10
    -> AttributeRounder_3
Junction_4
    -> AttributeRounder_3
Junction_6
    -> AttributeRounder_3
Junction_12
    -> AttributeRounder_3
Junction_14
    -> AttributeRounder_3
Junction_16
    -> AttributeRounder_3
Junction_18
    -> AttributeRounder_3
Junction_20
    -> AttributeRounder_3
Junction_28
    -> AttributeRounder_3
Junction_22
    -> AttributeRounder_3
Junction_24
    -> AttributeRounder_3
Junction_26
    -> AttributeRounder_3
Junction_30
    -> AttributeRounder_3
Junction_32
    -> AttributeRounder_3
Junction_34
    -> AttributeRounder_3
Junction_36
    -> AttributeRounder_3
Junction_38
    -> AttributeRounder_3
Junction_40
    -> AttributeRounder_3
Junction_42
    -> AttributeRounder_3
Junction_44
    -> AttributeRounder_3
Junction_46
    -> AttributeRounder_3
Junction_48
    -> AttributeRounder_3
Junction_50
    -> AttributeRounder_3
Junction_52
    -> AttributeRounder_3
Junction_54
    -> AttributeRounder_3
Junction_56
    -> AttributeRounder_3
Junction_58
    -> AttributeRounder_3
Junction_62
    -> AttributeRounder_3
Junction_60
    -> AttributeRounder_3
AttributeRounder_3
    SRC_ATTRS = MEASURE_TO MEASURE_FROM
    ROUND_TYPE = Nearest
    PLACES = 3
    -> VertexCreator
Note: Replace geometry from measures
VertexCreator
    XVAL = @Value(MEASURE_FROM)
    YVAL = 0
    MODE_NAME = Replace with Point
    -> VertexCreator_2
VertexCreator_2
    XVAL = @Value(MEASURE_TO)
    YVAL = 0
    MODE_NAME = Add Point
    -> AttributeKeeper_2
AttributeKeeper_2
    KEEP_ATTRS = STATE_CODE_RIGHT,TAG_REVENUE_ELIGIBLE,MEASURE_TO,STATE_CODE_LEFT,MILEAGE_CLASS,SAMPLE_ID,SHOULDER_PVD_WIDTH_IN_RT,SHOULDER_PVD_WIDTH_OUT_LT,STREET_SUFFIX_CD,NLF_ID,BASE_TYPE_LEFT_CD,STREET_NAME,TWP_CODE_RIGHT,DIVIDED_HWY_IND,MUNI_CODE_RIGHT,NHS_INTERMODAL_ROUTE_CD,SCENIC_ROUTE_NUMBER,SURFACE_TYPE_LEFT_CD,TRANSACTION_REASON_CODE,ACCESS_CONTROL_OPNL_CD,COUNTY_CODE_LEFT,COUNTY,TWP_CODE_LEFT,SCENIC_BYWAY_CD,NHS_CD,MEDIAN_TYPE_CD,ROADWAY_CLASS,ROUTE,BASE_TYPE_RIGHT_CD,MEASURE_FROM,STREET_DIR_SUFFIX_CD,FACILITY_TYPE_CD,ROUTE_SUFFIX,SURFACE_TYPE_RIGHT_CD,OWNERSHIP_CD,PRIORITY_SYSTEM_CD,SHOULDER_PVD_WIDTH_IN_LT,DIRECTION_OF_TRAVEL_CD,D_DISTRICT_ID,SURFACE_WIDTH_LEFT,SURFACE_WIDTH_RIGHT,ROUTE_TYPE,SHOULDER_TOTAL_WIDTH_RT,AREA_CODE_NBR,SPEED_LIMIT_NBR,OVERLAP_INDICATOR,COUNTY_SPLIT_INDICATOR,FUNCTION_CLASS_CD,COUNTY_CODE,JURISDICTION,LANES_NBR,MUNI_CODE_LEFT,MAINTENANCE_AUTHORITY_CD,ACCESS_CONTROL_CD,ROADWAY_WIDTH,STREET_PREFIX_DIR_CD,SHOULDER_PVD_WIDTH_OUT_RT,MEDIAN_WIDTH_NBR,SHOULDER_TYPE_CD,COUNTY_CODE_RIGHT,SHOULDER_TOTAL_WIDTH_LT,TRUCK_ROUTE_IND,FAP_IND,LANE_WIDTH_NBR
    -> Sorter_2
Sorter_2
    SORT_PARM = NLF_ID ALPHA ASCENDING MEASURE_FROM NUMERIC ASCENDING
    SORTED -> LineOnLineOverlayer [LINE]

Bookmark: Incoming data - Point features
RH.LRSE_LEAVE_REENTER (reader GEODATABASE_SDE_1)
    attributes: OBJECTID integer, LEAVE_REENTER_ID char(38), NLF_ID char(14), MEASURE_FROM double, MEASURE_TO double, LEAVE_IND char(1), REENTER_IND char(1), RH_DATE_ESTABLISH date, RH_DATE_RETIRE date, SYSTEM_DATE_CREATE date, SYSTEM_DATE_MOD date, USER_CREATE char(100), USER_MOD char(100), LOCERROR char(100), SHAPE.LEN double
    -> AttributeRounder_4
AttributeRounder_4
    SRC_ATTRS = MEASURE_TO MEASURE_FROM
    ROUND_TYPE = Nearest
    PLACES = 3
    -> Tester
    -> Tester_2
Tester
    TEST_MODE = Automatic
    BOOL_OP = OR
    TEST_CLAUSE = TEST @Value(REENTER_IND) = Y
    TEST_DESCRIPTION = ""
    PASSED -> VertexCreator_5
VertexCreator_5
    XVAL = @Value(MEASURE_FROM)
    YVAL = 0
    MODE_NAME = Replace with Point
    -> AttributeKeeper
    -> Junction_63
Junction_63
    -> Junction_64
Tester_2
    TEST_MODE = Automatic
    BOOL_OP = OR
    TEST_CLAUSE = TEST @Value(LEAVE_IND) = Y
    TEST_DESCRIPTION = ""
    PASSED -> VertexCreator_4
VertexCreator_4
    XVAL = @Value(MEASURE_TO)
    YVAL = 0
    MODE_NAME = Replace with Point
    -> AttributeKeeper
    -> Junction_65
Junction_65
    -> Junction_66
RH.LRSE_SEGMENT_DESCRIPTION (reader GEODATABASE_SDE_1)
    attributes: OBJECTID integer, SEGMENT_DESC_ID char(38), NLF_ID char(14), MEASURE_FROM double, MEASURE_TO double, SEGMENT_DESCRIPTION_TXT char(255), RH_DATE_ESTABLISH date, RH_DATE_RETIRE date, SYSTEM_DATE_CREATE date, SYSTEM_DATE_MOD date, USER_CREATE char(100), USER_MOD char(100), LOCERROR char(100), SHAPE.LEN double
    -> AttributeRounder
AttributeRounder
    SRC_ATTRS = MEASURE_TO MEASURE_FROM
    ROUND_TYPE = Nearest
    PLACES = 3
    -> VertexCreator_3
VertexCreator_3
    XVAL = @Value(MEASURE_FROM)
    YVAL = 0
    MODE_NAME = Replace with Point
    -> AttributeKeeper
    -> Junction_67
Junction_67
    -> Junction_68
AttributeKeeper
    KEEP_ATTRS = NLF_ID
    -> PointOnLineOverlayer [POINT]

Bookmark: Append information
Junction_64
    -> FeatureMerger_2 [SUPPLIER]
Junction_66
    -> FeatureMerger_3 [SUPPLIER]
Junction_68
    -> FeatureMerger [SUPPLIER]
Note: Segment Description attribute append
FeatureMerger
    ATTR_CONFLICT_RES = Use Requestor
    CONNECT_Z_MODE = First Wins
    ATTR_ACCUM_MODE = Merge Supplier
    JOIN_KEYS = @Value(NLF_ID) @Value(NLF_ID) AUTO @Value(MEASURE_FROM) @Value(MEASURE_FROM) AUTO
    GROUP_BY = NLF_ID
    PROCESS_DUPS = Yes
    SUPPLIERS_FIRST = No
    IGNORE_NULLS = No
    MERGE_TYPE = Attributes Only
    REJECT_NULL_MISSING_KEYS = No
    GEOM_TYPE = Build Polygons
    MERGED -> FeatureMerger_2 [REQUESTOR]
    UNMERGED_REQUESTOR -> FeatureMerger_2 [REQUESTOR]
Note: Reenter attribute append
FeatureMerger_2
    ATTR_CONFLICT_RES = Use Requestor
    CONNECT_Z_MODE = First Wins
    ATTR_ACCUM_MODE = Merge Supplier
    JOIN_KEYS = @Value(NLF_ID) @Value(NLF_ID) AUTO @Value(MEASURE_FROM) @Value(MEASURE_FROM) AUTO
    GROUP_BY = NLF_ID
    PROCESS_DUPS = Yes
    SUPPLIERS_FIRST = No
    IGNORE_NULLS = No
    MERGE_TYPE = Attributes Only
    REJECT_NULL_MISSING_KEYS = No
    GEOM_TYPE = Build Polygons
    MERGED -> FeatureMerger_3 [REQUESTOR]
    UNMERGED_REQUESTOR -> FeatureMerger_3 [REQUESTOR]
Note: Leave attribute append
FeatureMerger_3
    ATTR_CONFLICT_RES = Use Requestor
    CONNECT_Z_MODE = First Wins
    ATTR_ACCUM_MODE = Merge Supplier
    JOIN_KEYS = @Value(NLF_ID) @Value(NLF_ID) AUTO @Value(MEASURE_TO) @Value(MEASURE_TO) AUTO
    GROUP_BY = NLF_ID
    PROCESS_DUPS = Yes
    SUPPLIERS_FIRST = No
    IGNORE_NULLS = No
    MERGE_TYPE = Attributes Only
    REJECT_NULL_MISSING_KEYS = No
    GEOM_TYPE = Build Polygons
    MERGED -> NullAttributeMapper
    UNMERGED_REQUESTOR -> NullAttributeMapper
Note: Map Segment Description / missing to null
NullAttributeMapper
    SOURCE_ATTR_VAL = Empty "Missing (Selected Attributes Only)" Null
    NULL_TREATMENT = Null
    ATTRCHOICE = Selected Attributes
    ATTRLIST = SEGMENT_DESCRIPTION_TXT
    -> NullAttributeMapper_2
Note: Map leave and reenter / missing to N
NullAttributeMapper_2
    SOURCE_ATTR_VAL = Empty "Missing (Selected Attributes Only)" Null
    NEW_VALUE = N
    NULL_TREATMENT = New Value
    ATTRCHOICE = Selected Attributes
    ATTRLIST = LEAVE_IND REENTER_IND
    -> Tester_3
Note: Filter out zero length segments
Tester_3
    TEST_MODE = Automatic
    BOOL_OP = OR
    TEST_CLAUSE = TEST @Value(MEASURE_FROM) != @Value(MEASURE_TO)
    TEST_DESCRIPTION = ""
    PASSED -> DateTimeStamper
DateTimeStamper
    DATETIME_ATTR = _timestamp
    TIMEZONE = local
    STAMP_TYPE = date
    -> FeatureMerger_4 [REQUESTOR]

Bookmark: SpatialOverlayer
Note: Overlay measure geometry
LineOnLineOverlayer
    SEPARATE_COLLINEAR_SEGMENTS = No
    GENERATE_LIST_DROP = NO
    GROUP_BY = NLF_ID
    ATTRS_ACCUM_MODE = Merge Attributes
    DEAGGREGATE_INPUT = Yes
    LOG_LEVEL = Limited
    LINE -> PointOnLineOverlayer [LINE]
    <REJECTED> -> LineOnLineOverlayer__Rejected_
PointOnLineOverlayer
    ATTR_CONFLICT_RES = Use Original
    ATTR_ACCUM_MODE = Merge Incoming
    TOLERANCE = 0
    GROUP_BY = NLF_ID
    DEAGGREGATE_INPUT = Yes
    LINE -> CoordinateExtractor
    <REJECTED> -> PointOnLineOverlayer__Rejected_
Note: Extract new measures
CoordinateExtractor
    MODE = Specify Coordinate
    X_ATTR = MEASURE_FROM
    IND = 0
    -> CoordinateExtractor_2
CoordinateExtractor_2
    MODE = Specify Coordinate
    X_ATTR = MEASURE_TO
    IND = -1
    -> AttributeRounder_2
AttributeRounder_2
    SRC_ATTRS = MEASURE_TO MEASURE_FROM
    ROUND_TYPE = Nearest
    PLACES = 3
    -> FeatureMerger [REQUESTOR]
PointOnLineOverlayer__Rejected_: Inspector [off]
LineOnLineOverlayer__Rejected_: Inspector [off]

Bookmark: Population
RH.BNDY_CITY (reader GEODATABASE_SDE_2)
    attributes: OBJECTID integer, AREA_ID double, CORPORATION_NAME char(25), COUNTY_CODE char(3), FIPS_CODE char(9), ODOT_DISTRICT smallint, POP_2000 double, POP_1990 double, URBAN_AREA_CODE_OLD char(3), COLOR_CODE char(1), AREA_SQMI double, POPULATION double, URBAN_AREA_CODE char(9), USER_CREATE char(255), SYSTEM_CREATE_DATE date, USER_MOD char(255), SYSTEM_DATE_MOD date, SHAPE.AREA double, SHAPE.LEN double
    -> FeatureMerger_4 [SUPPLIER]
    -> FeatureMerger_5 [SUPPLIER]
FeatureMerger_4
    CONNECT_Z_MODE = First Wins
    ATTR_ACCUM_MODE = Prefix Supplier
    JOIN_KEYS = @Substring(@Value(MUNI_CODE_LEFT),-5,5) @Value(FIPS_CODE) AUTO
    SUPPLIER_PREFIX = LEFT_
    PROCESS_DUPS = Yes
    SUPPLIERS_FIRST = No
    IGNORE_NULLS = No
    MERGE_TYPE = Attributes Only
    REJECT_NULL_MISSING_KEYS = No
    GEOM_TYPE = Build Polygons
    MERGED -> FeatureMerger_5 [REQUESTOR]
FeatureMerger_5
    CONNECT_Z_MODE = First Wins
    ATTR_ACCUM_MODE = Prefix Supplier
    JOIN_KEYS = @Substring(@Value(MUNI_CODE_RIGHT),-5,5) @Value(FIPS_CODE) AUTO
    SUPPLIER_PREFIX = RIGHT_
    PROCESS_DUPS = Yes
    SUPPLIERS_FIRST = No
    IGNORE_NULLS = No
    MERGE_TYPE = Attributes Only
    REJECT_NULL_MISSING_KEYS = No
    GEOM_TYPE = Build Polygons
    MERGED -> AttributeManager

Bookmark: Subcomponents
AttributeManager
    ATTR_TABLE:
      SET_TO JURISDICTION = @Substring(@Value(NLF_ID),0,1)
      SET_TO ROUTE_TYPE = @Substring(@Value(NLF_ID),4,2)
      SET_TO ROUTE = @Substring(@Value(NLF_ID),6,5)
      SET_TO ROUTE_SUFFIX = @Substring(@Value(NLF_ID),11,1)
      SET_TO COUNTY = @Substring(@Value(NLF_ID),1,3)
      SET_TO DIRECTION_OF_TRAVEL_CD = @Substring(@Value(NLF_ID),13,1)
      SET_TO SEGMENT_DESCRIPTION_TXT = @Substring(@Value(NLF_ID),12,1)
    -> LineCombiner

Bookmark: Overlay geometry
GeometryRemover
    -> Overlay_geometry [RI]
RH.LRSN_COUNTY_NETWORK (reader GEODATABASE_SDE_1)
    attributes: OBJECTID integer, JURISDICTION char(1), COUNTY char(3), ROUTE_TYPE char(2), ROUTE_NUM char(5), LOCAL_ROUTE_SUFFIX char(1), STATE_ROUTE_SUFFIX char(1), CARDINALITY char(1), RH_DATE_ESTABLISH date, RH_DATE_RETIRE date, NLF_ID char(14), CREATED_USER char(255), CREATED_DATE date, LAST_EDITED_USER char(255), LAST_EDITED_DATE date, SHAPE.LEN double
    -> Overlay_geometry [COUNTY_NETWROK]
Overlay_geometry: Overlay geometry
    FME_RI_events -> AttributeExposer
Note: change nlfid measure from measure to attribute names
AttributeExposer
    ATTR_LIST = MUNI_CODE_LEFT,SHOULDER_PVD_WIDTH_OUT_LT,LEFT_POPULATION,SCENIC_BYWAY_CD,AREA_CODE_NBR,TRANSACTION_REASON_CODE,SURFACE_WIDTH_RIGHT,TWP_CODE_RIGHT,ROADWAY_CLASS,SAMPLE_ID,SHOULDER_TOTAL_WIDTH_RT,FROMMEASURE,STATE_CODE_RIGHT,SHOULDER_TOTAL_WIDTH_LT,SURFACE_TYPE_LEFT_CD,MILEAGE_CLASS,SHOULDER_PVD_WIDTH_IN_LT,LANES_NBR,SHOULDER_PVD_WIDTH_OUT_RT,LEAVE_IND,REENTER_IND,SHOULDER_TYPE_CD,COUNTY_CODE_RIGHT,OWNERSHIP_CD,STREET_DIR_SUFFIX_CD,TAG_REVENUE_ELIGIBLE,JURISDICTION,DIVIDED_HWY_IND,SURFACE_WIDTH_LEFT,STREET_PREFIX_DIR_CD,OVERLAP_INDICATOR,ACCESS_CONTROL_OPNL_CD,MEDIAN_WIDTH_NBR,ACCESS_CONTROL_CD,LANE_WIDTH_NBR,FACILITY_TYPE_CD,MAINTENANCE_AUTHORITY_CD,ROUTEID,BASE_TYPE_LEFT_CD,MEDIAN_TYPE_CD,NHS_CD,COUNTY_CODE_LEFT,FUNCTION_CLASS_CD,FAP_IND,ROUTE_TYPE,TOMEASURE,ROUTE,STREET_NAME,ROADWAY_WIDTH,MUNI_CODE_RIGHT,STATE_CODE_LEFT,D_DISTRICT_ID,RIGHT_POPULATION,SCENIC_ROUTE_NUMBER,SPEED_LIMIT_NBR,TWP_CODE_LEFT,SURFACE_TYPE_RIGHT_CD,BASE_TYPE_RIGHT_CD,DIRECTION_OF_TRAVEL_CD,TRUCK_ROUTE_IND,ROUTE_SUFFIX,PRIORITY_SYSTEM_CD,STREET_SUFFIX_CD,COUNTY_SPLIT_INDICATOR,COUNTY,NHS_INTERMODAL_ROUTE_CD,SEGMENT_DESCRIPTION_TXT,SHOULDER_PVD_WIDTH_IN_RT,COUNTY_CODE,LEFT_POPULATION,RIGHT_POPULATION
    -> FME_RI_events (writer FILEGDB_2)

FME custom transformer SpatialOverlayer_2

Parameters:
- MEASURE_FROM = @Value(MEASURE_FROM)   # Measure From
- NLF_ID = @Value(NLF_ID)   # Nlf Id
- MEASURE_TO = @Value(MEASURE_TO)   # Measure To

Bookmark: SpatialOverlayer
Sorter_2_Input_1 (input)
    -> Sorter_2
Sorter_2
    SORT_PARM = NLF_ID ALPHA ASCENDING MEASURE_FROM NUMERIC ASCENDING MEASURE_TO NUMERIC ASCENDING
    SORTED -> VertexCreator
Note: Replace geometry from measures
VertexCreator
    XVAL = @Value(MEASURE_FROM)
    YVAL = 0
    MODE_NAME = Replace with Point
    -> VertexCreator_2
VertexCreator_2
    XVAL = @Value(MEASURE_TO)
    YVAL = 0
    MODE_NAME = Add Point
    -> LineOnLineOverlayer [LINE]
Note: Overlay measure geometry
LineOnLineOverlayer
    SEPARATE_COLLINEAR_SEGMENTS = No
    GENERATE_LIST_DROP = NO
    GROUP_BY = NLF_ID
    ATTRS_ACCUM_MODE = Merge Attributes
    DEAGGREGATE_INPUT = Yes
    LOG_LEVEL = Full
    LINE -> CoordinateExtractor
Note: Extract new measures
CoordinateExtractor
    MODE = Specify Coordinate
    X_ATTR = MEASURE_FROM
    IND = 0
    -> CoordinateExtractor_2
CoordinateExtractor_2
    MODE = Specify Coordinate
    X_ATTR = MEASURE_TO
    IND = 1
    -> Sorter
Sorter
    SORT_PARM = NLF_ID ALPHA ASCENDING MEASURE_FROM NUMERIC ASCENDING MEASURE_TO NUMERIC ASCENDING
    SORTED -> Sorter_Sorted_1 (output)
Sorter_Sorted_1 (output)

FME custom transformer SchemaSetter
This transformer adds both exposed and unexposed attributes to a feature-based schema, with appropriate data types. 
For example: if a feature has the following attributes:
    Attribute(boolean) : `mybool' has value `Yes'
    Attribute(32 bit integer): `myint' has value `12'
    Attribute(64 bit real) : `myreal' has value `12.965'
the following list attributes will be added:
    Attribute(string) : `attribute{0}.fme_data_type' has value `fme_boolean' 
    Attribute(encoded: utf-8): `attribute{0}.name' has value `mybool' 
    Attribute(string) : `attribute{1}.fme_data_type' has value `fme_int32' 
    Attribute(encoded: utf-8): `attribute{1}.name' has value `myint' 
    Attribute(string) : `attribute{2}.fme_data_type' has value `fme_real64' 
    Attribute(encoded: utf-8): `attribute{2}.name' has value `myreal' 
The transformer also gives users the option to exclude certain attributes based on name or prefix, and automatically excludes all "fme_" attributes.
Input Ports
Features containing attributes for which a schema definition is required. 
    Output Ports
All features are output. Attributes which have been selected to be excluded are removed from the feature. The list containing the schema of the feature is added to each feature. 
    Parameters
    Attributes to Exclude
A selected set of attributes that will be excluded from the generated schema list and removed from the feature.
    Prefixes to Exclude
A comma-delimited list of prefixes for attributes that are to be excluded from the generated schema list and removed from the feature. Regular expressions are not supported. For example: "date" will exclude any attributes that start with the letters "date" e.g. date_created, dateupdated
    Sort Attributes
(Ascending, Descending, None) Set this parameter to alphabetically sort output attributes.
    Usage Notes
The feature based schema can be passed to any writer that it set to Dynamic Mode and used with the "Schema from First Feature" setting.
Please see 
        https://knowledge.safe.com/articles/1051/dynamic-workflow-tutorial-destination-schema-is-de-2.html 
    for more information on feature-based schema using list attributes.

Parameters:
- AttributesToExclude =   # " " Attributes to exclude
- PrefixesToExclude =   # Prefixes to exclude
- SORT = None   # Sort Attributes

Input (input)
    -> ParameterFetcher
Note: Retrieve Parameters
ParameterFetcher
    ATTR_LIST = _AttributesToExclude {$(AttributesToExclude)} _PrefixesToExclude {$(PrefixesToExclude)} _sort {$(SORT)}
    -> PythonCaller
Note: See Comment in Code
PythonCaller
    PYTHONSYMBOL = FeatureProcessor
    PYTHONSOURCE:
      from __future__ import absolute_import, division, print_function, unicode_literals

      import fmeobjects
      import six

      #Checks if a list entry starts with a certain string
      def StringLikeList(list,string):
              test=False
              for element in list:
                  if string.startswith(element):
                      test=True
              return test

       # Checks if a list contains an element equal to a certain string
      def StringInList(list,string):
              test=False
              for element in list:
                  if string==element:
                      test=True
              return test

      # Template Class Interface:
      class FeatureProcessor(object):

          typesMapping = {
              fmeobjects.FME_ATTR_UNDEFINED : None,
              fmeobjects.FME_ATTR_BOOLEAN : "fme_boolean",
              fmeobjects.FME_ATTR_INT8 : "fme_int8",
              fmeobjects.FME_ATTR_UINT8 : "fme_uint8",
              fmeobjects.FME_ATTR_INT16 : "fme_int16",
              fmeobjects.FME_ATTR_UINT16 : "fme_uint16",
              fmeobjects.FME_ATTR_INT32 : "fme_int32",
              fmeobjects.FME_ATTR_UINT32 : "fme_uint32",
              fmeobjects.FME_ATTR_REAL32 : "fme_real32",
              fmeobjects.FME_ATTR_REAL64 : "fme_real64",
              fmeobjects.FME_ATTR_REAL80 : "fme_real80",
              fmeobjects.FME_ATTR_STRING : "fme_char(255)",
              fmeobjects.FME_ATTR_ENCODED_STRING : "fme_varchar(255)",
              fmeobjects.FME_ATTR_INT64 : "fme_int64",
              fmeobjects.FME_ATTR_UINT64 : "fme_uint64"
           }

          def __init__(self):
              pass
          def input(self,feature):
              #create a new feature
              nfeature=fmeobjects.FMEFeature()
              #get list of all attributes on feature
              attlist=feature.getAllAttributeNames()
              #loop through all attributes and add to schema if they fail exclusion criteria
              i=0
              ExcludedAttributes=str(feature.getAttribute('_AttributesToExclude')).split(",")
              ExcludedPrefixes=str(feature.getAttribute('_PrefixesToExclude')).split(",")

              # remove all fme_ attributes from list - don't want to include these in dynamic schema
              ExcludedPrefixes = ['fme_'] if ExcludedPrefixes == [''] else ExcludedPrefixes + ["fme_"]

              # sorting attributes
              if feature.getAttribute('_sort') == 'Ascending' or feature.getAttribute('_sort') == 'Descending':
                  attlist.sort()
                  if feature.getAttribute('_sort') == 'Descending':
                      attlist.reverse()

              for att in attlist:
                  if not StringInList(ExcludedAttributes,att) and not StringLikeList(ExcludedPrefixes,att) and not att=='_AttributesToExclude' and not att=='_PrefixesToExclude' and not att=='_sort':
                     type=feature.getAttributeType(att)
                     #Check datatype and set in schema
                     type = self.typesMapping[type]

                     if type is None:
                         feature.removeAttribute(att)
                     else:
                         #add schema attributes to feature
                         nfeature.setAttribute("attribute{"+str(i)+"}.fme_data_type",type)
                         nfeature.setAttribute("attribute{"+str(i)+"}.name",six.text_type(att))
                         nfeature.setAttribute(att,feature.getAttribute(att))
                         i+=1;
              #copy original geometry to new feature
              nfeature.setGeometry(feature.getGeometry())
              nfeature.setCoordSys(feature.getCoordSys())
              nfeature.setFeatureType(feature.getFeatureType())
              nfeature.setAttribute("fme_geometry{0}",feature.getAttribute("fme_type"))
              nfeature.setAttribute("fme_feature_type",feature.getAttribute("fme_feature_type"))
              self.pyoutput(nfeature)
          def close(self):
              pass
    -> Output (output)
Output (output)

FME custom transformer Overlay geometry

Note: COUNTY_NETWROK
COUNTY_NETWROK (input)
    -> AttributeCreator_2
Note: Set the input feature type
AttributeCreator_2
    ATTR_TABLE = SET_TO fme_feature_type = COUNTY_NETWORK
    -> Sampler
Note: RI
RI (input)
    -> AttributeCreator
Note: Set the input feature type
AttributeCreator
    ATTR_TABLE = SET_TO fme_feature_type = RI
    -> VariableRetriever
Note: Fix path slashes
StringReplacer
    CASE = NO
    REPLACE_TEXT = /
    SRC_ATTRS = _dataset
    FIND_TEXT = \
    REGEXP = NO
    NO_MATCH = _FME_NO_OP_
    -> PythonCaller
Note: Computes the intersection of input features and route features and / writes the route and measure information to a new event table
PythonCaller
    PYTHONSYMBOL = processFeature
    PYTHONSOURCE:
      import fme
      import fmeobjects
      import arcpy

      def processFeature(feature):
          # Get dissolve FC and settings from feature attributes
          dataset = feature.getAttribute('_dataset')
          arcpy.env.workspace = dataset

          props = "NLF_ID LINE MEASURE_FROM MEASURE_TO"
          outFeatureClass = dataset + "/RI_events"
          arcpy.MakeRouteEventLayer_lr ('COUNTY_NETWORK', 'NLF_ID','RI',props,"RI_events_layer")
          arcpy.CopyFeatures_management("RI_events_layer", outFeatureClass)
          arcpy.Delete_management("RI_events_layer")
    -> FeatureReader [INITIATOR]
Note: Read back output feature class
FeatureReader
    FEATURETYPES = RI_events
    INTERACT = <No Spatial Filter>
    ATTR_ACCUM_MODE = Merge Initiator and Result
    DATASET = @Value(_dataset)
    COMBINE_GEOM = Use Result
    OUTPUT_FEATURES_DISPLAY = Schema and Data Features
    ATTR_CONFLICT_RES = Use Result
    FILEGDB_QUERY_FEATURE_TYPES_FOR_MERGE_FILTERS = Yes
    FORMAT = FILEGDB
    FILEGDB_USE_SEARCH_ENVELOPE = NO
    <OTHER> -> AttributeRemover
Note: Remove temporary attributes
AttributeRemover
    LIST_ATTRS = _feature_type{}
    REMOVE_ATTRS = _dataset,_total_features_written
    -> FME_RI_events (output)
FME_RI_events (output)

Bookmark: Set temporary GDB location
Sampler
    RATE = 1
    SAMPLE_MODE = No
    SAMPLE_TYPE_LONG = First N Features
    SAMPLED -> TempPathnameCreator
    NOT_SAMPLED -> VariableRetriever_2
Note: Create temp location
TempPathnameCreator
    PATHNAME_ATTR = _pathname
    -> VariableSetter
Note: Store temp location in variable
VariableSetter
    SCOPE = Local
    VARNAME = temp_path
    VALUE = @Value(_pathname)
    -> SchemaSetter
SchemaSetter
    SORT = None
    -> FeatureWriter [Output]
Note: Read temp location from variable
VariableRetriever_2
    VALUE_ATTR = _pathname
    SCOPE = Local
    VARNAME = temp_path
    -> FeatureWriter [Output]
Note: Read temp location from variable
VariableRetriever
    VALUE_ATTR = _pathname
    SCOPE = Local
    VARNAME = temp_path
    -> SchemaSetter_2
SchemaSetter_2
    SORT = None
    -> FeatureWriter [Output00]
Note: Write to temp gdb
FeatureWriter
    FEATURE_TYPE_LIST_ATTR = _feature_type
    TOTAL_FEATURES_WRITTEN_ATTR = _total_features_written
    FORMAT = FILEGDB
    DATASET = @Value(_pathname)\temp.gdb
    FILEGDB_DESTINATION_DATASETTYPE_VALIDATION = Yes
    DATASET_ATTR = _dataset
    FILEGDB_COORDINATE_SYSTEM_GRANULARITY = FEATURE_TYPE
    FILEGDB_OVERWRITE_GEODB = YES
    SUMMARY -> StringReplacer
